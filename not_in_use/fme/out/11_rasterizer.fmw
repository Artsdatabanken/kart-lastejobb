FME workspace 11_rasterizer.fmw

Parameters:
- datasetId = 5   # DatasetId
- prefix = NA
- DestDataset_ENVIHDR = D:\out\codecube   # Destination ITT ENVI .hdr RAW Raster Folder
- Resolution = 250
- DestDataset_PNGRASTER = D:\out\codecube   # Destination PNG (Portable Network Graphics) Folder
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_host:   # Python Script
      import fme
      import json
      
      data = json.load(open('../../config/postgis.json'))
      
      return data['host']
- config_port:   # Python Script
      import fme
      import json
      
      data = json.load(open('../../config/postgis.json'))
      
      return data['port']

Writers:
- ENVIHDR_1: ENVIHDR to $(DestDataset_ENVIHDR)
- PNGRASTER_1: PNGRASTER to $(DestDataset_PNGRASTER)

Creator
    GEOMTYPE = Geometry Object
    NUM = 1
    CREATED -> FeatureReader [INITIATOR]
    CREATED -> FeatureReader_4 [INITIATOR]
GeometryValidator__Rejected_: Inspector

Bookmark: Join
FeatureReader_4
    ATTRS_TO_EXPOSE = code geometry_id
    ATTR_ACCUM_MODE = Merge Initiator and Result
    ATTR_CONFLICT_RES = Use Result
    COMBINE_GEOM = Use Result
    DATASET = $(config_db)
    FEATURETYPES = data.codes_geometry
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_HOST = $(config_host)
    POSTGIS_PASSWORD = $(config_pass)
    POSTGIS_PORT = $(config_port)
    POSTGIS_POSTGIS_EXPOSE_FORMAT_ATTRS = postgres_oid,int4
    POSTGIS_QUERY_FEATURE_TYPES_FOR_MERGE_FILTERS = Yes
    POSTGIS_USER_NAME = $(config_user)
    POSTGIS_USE_SEARCH_ENVELOPE = NO
    POSTGIS_USE_TRUE_POSTGIS_TYPES = yes
    <OTHER> -> FeatureMerger_3 [REQUESTOR]
    <REJECTED> -> FeatureReader__Rejected_
FeatureReader
    ATTRS_TO_EXPOSE = id
    ATTR_ACCUM_MODE = Only Use Result
    COMBINE_GEOM = Use Result
    DATASET = bigbadabom
    FEATURETYPES = data.geometry
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = bigbadabom
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> FeatureMerger_3 [SUPPLIER]
    <REJECTED> -> FeatureReader__Rejected_
FeatureMerger_3
    ATTR_ACCUM_MODE = Merge Supplier
    ATTR_CONFLICT_RES = Use Requestor
    IGNORE_NULLS = No
    JOIN_KEYS = @Value(geometry_id) @Value(id) AUTO
    MERGE_TYPE = Attributes and Geometry
    PROCESS_DUPS = NO
    REJECT_NULL_MISSING_KEYS = Yes
    SUPPLIERS_FIRST = No
    MERGED -> Deaggregator
FeatureReader__Rejected_: Logger
    LOG_FEATURE = LOG_ONLY
    MAXCOORDS = 20
    MAXFEATS = 20
    MESSAGE = Feature is:
    SEVERITY = INFO

Bookmark: Prepare
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> GeometryValidator
GeometryValidator
    ISSUE_ATTR_NAME = _issues
    PRESETS = Basic Integrity
    REPAIR = Yes
    RULES = NAN_REMOVAL PROCESS_MEASURE]NO]FME_CONTROLLER_QUERY_FILE]transformers\dependencies\geometryvalidator\NAN_REMOVAL.fme NULL_REMOVAL  TYPE_REPAIR CONNECT_Z_MODE]FIRST_WINS]ARC_ENDPOINT_TOLERANCE_MODE]Auto]ARC_ENDPOINT_TOLERANCE]<Unused>]FME_CONTROLLER_QUERY_FILE]transformers\dependencies\geometryvalidator\TYPE_REPAIR.fme
    SUMMARY = Detailed
    PASSED -> Reprojector
    REPAIRED -> Reprojector
    <REJECTED> -> GeometryValidator__Rejected_
Reprojector
    DEST = EPSG:3857
    INTERPOLATION_TYPE_NAME = Nearest Neighbor
    RASTER_CELL_SIZE = Preserve Cells
    RASTER_TOLERANCE = 0.0
    SOURCE = EPSG:4326
    REPROJECTED -> 3DForcer
3DForcer
    KEEPZVAL = No
    ZVALATTR = 255
    -> Aggregator
Aggregator
    ACCUM_ATTRS_NAME = Use Attributes From One Feature
    AGGREGATE_TYPE = Homogeneous Collection (If Possible)
    GROUP_BY = code
    MODE = Geometry - Assemble One Level
    ORDERED = No
    SEP = ,
    AGGREGATE -> BoundsExtractor

Bookmark: Rasterize
BoundsExtractor
    XMAX = _xmax
    XMIN = _xmin
    YMAX = _ymax
    YMIN = _ymin
    ZMAX = _zmax
    ZMIN = _zmin
    -> NumericRasterizer_2
NumericRasterizer_2
    ANTI_ALIASING = No
    BACKGROUND_VALUE = 0
    FILL_WITH_NODATA = Yes
    GROUND_EXTENTS_MAX_X = (@int((@Value(_xmax)/$(Resolution))) * $(Resolution)) + $(Resolution)
    GROUND_EXTENTS_MAX_Y = (@int((@Value(_ymax)/$(Resolution))) * $(Resolution)) +$(Resolution)
    GROUND_EXTENTS_MIN_X = (@int((@Value(_xmin)/$(Resolution))) * $(Resolution) )- $(Resolution)
    GROUND_EXTENTS_MIN_Y = (@int((@Value(_ymin)/$(Resolution))) * $(Resolution)) - $(Resolution)
    GROUP_BY = code
    INTERPRETATION_TYPE = UInt8
    ROWCOL_OR_CELLSIZE = CellSize
    SPECIFY_GROUND_EXTENTS = Specify ground extents
    TOLERANCE = 0.5
    X_CELL_SIZE = 250
    Y_CELL_SIZE = 250
    RASTER -> StringReplacer
    <REJECTED> -> NumericRasterizer_2__Rejected_
StringReplacer
    CASE = NO
    FIND_TEXT = -
    NO_MATCH = _FME_NO_OP_
    REGEXP = NO
    REPLACE_TEXT = \
    SRC_ATTRS = code
    -> raster.observation.8bit.3857 (writer ENVIHDR_1) [off]
    -> RasterInterpretationCoercer
RasterInterpretationCoercer
    COLOR_TO_COLOR = Cast
    FLOAT_TO_INTEGER = Round
    INTERPRETATION = Gray8
    NUMERIC_TO_COLOR = Cast
    -> raster.observation.8bit.3857 (writer PNGRASTER_1)
raster.observation.8bit.3857 (writer PNGRASTER_1)
    attributes: code char(200)
raster.observation.8bit.3857 (writer ENVIHDR_1)
    attributes: code char(200)
NumericRasterizer_2__Rejected_: Logger
    LOG_FEATURE = LOG_ONLY
    MAXCOORDS = 20
    MAXFEATS = 20
    MESSAGE = Feature is:
    SEVERITY = INFO
