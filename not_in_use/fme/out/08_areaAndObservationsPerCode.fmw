FME workspace 08_areaAndObservationsPerCode.fmw

Parameters:
- DestDataset_TEXTLINE = D:\out\json\codes\areasAndObservationsPerCode.json   # Destination Text File
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_port:   # Python Script
      import fme
      import json
      
      data = json.load(open('../../config/postgis.json'))
      
      return data['port']
- config_host:   # Python Script
      import fme
      import json
      
      data = json.load(open('../../config/postgis.json'))
      
      return data['host']

Writers:
- TEXTLINE_1: TEXTLINE to $(DestDataset_TEXTLINE)

Creator
    GEOMTYPE = Geometry Object
    NUM = 1
    CREATED -> AttributeCreator
    CREATED -> SQLExecutor [INITIATOR]

Bookmark: Datasets
SQLExecutor
    SQL_STATEMENT:
      select
      d.id as dataset_id, p.value as prefix
      from
      data.dataset d, data.prefix p
      where
      d.prefix_id = p.id
    COMBINE_GEOM = Initiator Geometry Only
    POSTGRES_PASSWORD = $(config_pass)
    COMBINE_ATTRS = Result Attributes Only
    EXPOSED_ATTRIBUTE_LIST = dataset_id,prefix
    DATASET = $(config_db)
    POSTGRES_USER_NAME = $(config_user)
    FORMAT = POSTGRES
    POSTGRES_QUERY_FEATURE_TYPES_FOR_MERGE_FILTERS = Yes
    POSTGRES_PORT = 5432
    POSTGRES_HOST = $(config_host)
    RESULT -> AttributeFilter
AttributeFilter
    ATTR_VALUES = <Empty>,<Missing>,<Null>,<Unfiltered>,AR
    ATTR_NAME = prefix
    <UNFILTERED> -> FeatureMerger [SUPPLIER]
    AR -> FeatureMerger_2 [SUPPLIER]

Bookmark: Geometries
AttributeCreator
    ATTR_TABLE = SET_TO id
    -> FeatureReader [INITIATOR]
FeatureReader
    POSTGIS_FEATURES_PER_FETCH = 10000
    COMBINE_GEOM = Use Result
    POSTGIS_HOST = $(config_host)
    POSTGIS_PORT = $(config_port)
    ATTR_CONFLICT_RES = Use Result
    ATTR_ACCUM_MODE = Merge Initiator and Result
    INTERACT = <No Spatial Filter>
    FORMAT = POSTGIS
    POSTGIS_DISABLE_COLLECTION_SPLITTING = yes
    POSTGIS_USER_NAME = $(config_user)
    FEATURETYPES = data.geometry
    POSTGIS_POSTGIS_EXPOSE_FORMAT_ATTRS = postgres_oid,int4
    ATTRS_TO_EXPOSE = dataset_id
    POSTGIS_USE_TRUE_POSTGIS_TYPES = yes
    DATASET = $(config_db)
    OUTPUT_FEATURES_DISPLAY = Schema and Data Features
    POSTGIS_QUERY_FEATURE_TYPES_FOR_MERGE_FILTERS = Yes
    POSTGIS_PASSWORD = $(config_pass)
    POSTGIS_USE_SEARCH_ENVELOPE = NO
    <OTHER> -> AttributeRenamer
AttributeRenamer
    ATTR_TABLE = RENAME_SET_DEFAULT id > geometry_id
    -> Reprojector_2
Reprojector_2
    DEST = EPSG:25833
    RASTER_CELL_SIZE = Preserve Cells
    INTERPOLATION_TYPE_NAME = Nearest Neighbor
    SOURCE = EPSG:4326
    REPROJECTED -> FeatureMerger_2 [REQUESTOR]
    REPROJECTED -> FeatureMerger [REQUESTOR]

Bookmark: AR-geometry
FeatureMerger_2
    IGNORE_NULLS = No
    PROCESS_DUPS = No
    MERGE_TYPE = Attributes Only
    SUPPLIERS_FIRST = No
    JOIN_KEYS = @Value(dataset_id) @Value(dataset_id) AUTO
    REJECT_NULL_MISSING_KEYS = Yes
    ATTR_CONFLICT_RES = Use Requestor
    ATTR_ACCUM_MODE = Merge Supplier
    MERGED -> GeometryFilter
GeometryFilter
    GEOM_PORT_NAMES = Point Line Area Surface
    BREAK_AGG = No
    POINT -> AttributeRenamer_5
AttributeRenamer_5
    ATTR_TABLE = RENAME_SET_DEFAULT geometry_id > geometry_id_ar
    -> PointOnAreaOverlayer_2 [POINT]

Bookmark: All geometry sans AR
FeatureMerger
    IGNORE_NULLS = No
    PROCESS_DUPS = No
    MERGE_TYPE = Attributes Only
    SUPPLIERS_FIRST = No
    JOIN_KEYS = @Value(dataset_id) @Value(dataset_id) AUTO
    REJECT_NULL_MISSING_KEYS = Yes
    ATTR_CONFLICT_RES = Use Requestor
    ATTR_ACCUM_MODE = Merge Supplier
    MERGED -> PointOnAreaOverlayer_2 [AREA]
    MERGED -> AreaCalculator

Bookmark: Intersect geometry
PointOnAreaOverlayer_2
    CANDIDATE_LIST_ATTRS_TO_INCLUDE = geometry_id_ar
    OV_ATTR = _overlaps
    CANDIDATE_LIST_ATTRS_TO_INCLUDE_MODE = Selected Attributes
    POLYS_FIRST = NO
    CANDIDATE_LIST_NAME = _relationships
    ATTR_CONFLICT_RES = Use Original
    ATTR_ACCUM_MODE = Merge Incoming
    DEAGGREGATE_INPUT = Yes
    AREA -> Tester_2
    <REJECTED> -> PointOnAreaOverlayer_2__Rejected_
PointOnAreaOverlayer_2__Rejected_: Logger
    MAXCOORDS = 20
    MESSAGE = Feature is:
    MAXFEATS = 20
Tester_2
    TEST_CLAUSE = TEST @Value(_overlaps) > 0
    BOOL_OP = OR
    TEST_DESCRIPTION = ""
    TEST_MODE = Automatic
    PASSED -> GeometryRemover
GeometryRemover
    -> ListExploder_2

Bookmark: Join in AR-codes
ListExploder_2
    ATTR_CONFLICT_RES = Use List Attribute Values
    ATTR_ACCUM_MODE = Merge List Attributes
    LIST_ATTR = _relationships{}
    INDEX_ATTR = _element_index
    ELEMENTS -> DatabaseJoiner_2
DatabaseJoiner_2
    POSTGRES_PASSWORD = $(config_pass)
    TABLE = data.codes_geometry
    CACHE_SIZE = 5000
    ADDED_FIELDS = code
    MATCH_MULTIPLE_DISPLAY = Create a feature for each match
    DATASET = $(config_db)
    POSTGRES_USER_NAME = $(config_user)
    FORMAT = POSTGRES
    JOIN_KEYS = geometry_id_ar geometry_id
    PREFETCH_EXHAUSTIVE = Yes
    ATTR_CONFLICT_RES = Use Original
    POSTGRES_QUERY_FEATURE_TYPES_FOR_MERGE_FILTERS = Yes
    POSTGRES_PORT = 5432
    ATTR_ACCUM_MODE = Merge Joined
    MATCH_RULE_DISPLAY = Match All (1:M)
    POSTGRES_HOST = $(config_host)
    JOINED -> AttributeRenamer_4
AttributeRenamer_4
    ATTR_TABLE = RENAME_SET_DEFAULT code > code_ar
    -> AttributeValueMapper
    -> DatabaseJoiner_3 [off]
AttributeValueMapper
    VAL_ATTR = code_ar
    SRC = code_ar
    DIRECTION = Forward (Source To Destination)
    LUT = @Value(code_ar),@Substring(@Value(code_ar), 3)
    -> DatabaseJoiner

Bookmark: Only keep species or lower
DatabaseJoiner_3 [off]
    POSTGRES_PASSWORD = $(config_pass)
    TABLE = data.codes
    CACHE_SIZE = 5000
    ADDED_FIELDS = level
    MATCH_MULTIPLE_DISPLAY = Create a feature for each match
    DATASET = $(config_db)
    POSTGRES_USER_NAME = $(config_user)
    FORMAT = POSTGRES
    JOIN_KEYS = code_ar code
    PREFETCH_EXHAUSTIVE = Yes
    ATTR_CONFLICT_RES = Use Original
    POSTGRES_QUERY_FEATURE_TYPES_FOR_MERGE_FILTERS = Yes
    POSTGRES_PORT = 5432
    ATTR_ACCUM_MODE = Merge Joined
    MATCH_RULE_DISPLAY = Match All (1:M)
    POSTGRES_HOST = $(config_host)
    JOINED -> Tester [off]
Tester [off]
    TEST_CLAUSE = TEST @Value(level) > 7
    BOOL_OP = OR
    TEST_DESCRIPTION = ""
    TEST_MODE = Automatic
    PASSED -> DatabaseJoiner [off]

Bookmark: Join in other codes
DatabaseJoiner
    POSTGRES_PASSWORD = $(config_pass)
    TABLE = data.codes_geometry
    CACHE_SIZE = 5000
    ADDED_FIELDS = code
    MATCH_MULTIPLE_DISPLAY = Create a feature for each match
    DATASET = $(config_db)
    POSTGRES_USER_NAME = $(config_user)
    FORMAT = POSTGRES
    JOIN_KEYS = geometry_id geometry_id
    PREFETCH_EXHAUSTIVE = Yes
    ATTR_CONFLICT_RES = Use Original
    POSTGRES_QUERY_FEATURE_TYPES_FOR_MERGE_FILTERS = Yes
    POSTGRES_PORT = 5432
    ATTR_ACCUM_MODE = Merge Joined
    MATCH_RULE_DISPLAY = Match All (1:M)
    POSTGRES_HOST = $(config_host)
    JOINED -> AttributeKeeper
AttributeKeeper
    KEEP_ATTRS = code_ar,code,geometry_id
    -> Aggregator_2

Bookmark: Join in predecessor
Aggregator_2
    CONCAT_ATTRS = code_ar geometry_id
    GROUP_BY = code
    ORDERED = No
    ACCUM_ATTRS_NAME = Merge Incoming Attributes
    SEP = ,
    MODE = Attributes Only
    AGGREGATE -> AttributeKeeper_2
    AGGREGATE -> DatabaseJoiner_5
    AGGREGATE -> FeatureMerger_5 [SUPPLIER]
DatabaseJoiner_5
    POSTGRES_PASSWORD = $(config_pass)
    TABLE = data.codeshierarchy
    CACHE_SIZE = 5000
    ADDED_FIELDS = predecessor
    MATCH_MULTIPLE_DISPLAY = Create a feature for each match
    DATASET = $(config_db)
    POSTGRES_USER_NAME = $(config_user)
    FORMAT = POSTGRES
    JOIN_KEYS = code successor
    PREFETCH_EXHAUSTIVE = Yes
    ATTR_CONFLICT_RES = Use Original
    POSTGRES_QUERY_FEATURE_TYPES_FOR_MERGE_FILTERS = Yes
    POSTGRES_PORT = 5432
    ATTR_ACCUM_MODE = Merge Joined
    MATCH_RULE_DISPLAY = Match All (1:M)
    POSTGRES_HOST = $(config_host)
    JOINED -> Aggregator_5
Aggregator_5
    CONCAT_ATTRS = code_ar code geometry_id
    GROUP_BY = predecessor
    ORDERED = No
    ACCUM_ATTRS_NAME = Merge Incoming Attributes
    SEP = ,
    MODE = Attributes Only
    AGGREGATE -> PythonCaller
    AGGREGATE -> AttributeKeeper_3

Bookmark: Find codes not predecessors
AttributeKeeper_2
    KEEP_ATTRS = code
    -> FeatureMerger_4 [REQUESTOR]
AttributeKeeper_3
    KEEP_ATTRS = predecessor
    -> FeatureMerger_4 [SUPPLIER]
FeatureMerger_4
    IGNORE_NULLS = No
    PROCESS_DUPS = Yes
    MERGE_TYPE = Attributes Only
    SUPPLIERS_FIRST = No
    JOIN_KEYS = @Value(code) @Value(predecessor) AUTO
    REJECT_NULL_MISSING_KEYS = No
    ATTR_CONFLICT_RES = Use Requestor
    GEOM_TYPE = Build Polygons
    ATTR_ACCUM_MODE = Merge Supplier
    CONNECT_Z_MODE = First Wins
    UNMERGED_REQUESTOR -> AttributeCreator_2

Bookmark: Add back in AR for codes
AttributeCreator_2
    ATTR_TABLE = SET_TO predecessor = @Value(code)
    -> FeatureMerger_5 [REQUESTOR]
FeatureMerger_5
    IGNORE_NULLS = No
    PROCESS_DUPS = Yes
    MERGE_TYPE = Attributes Only
    SUPPLIERS_FIRST = No
    JOIN_KEYS = @Value(code) @Value(code) AUTO
    REJECT_NULL_MISSING_KEYS = No
    ATTR_CONFLICT_RES = Use Requestor
    GEOM_TYPE = Build Polygons
    ATTR_ACCUM_MODE = Merge Supplier
    CONNECT_Z_MODE = First Wins
    MERGED -> PythonCaller

Bookmark: Count unique values
PythonCaller
    NEW_ATTRIBUTES = _count_code_ar _count_geometry_id
    PYTHONSYMBOL = FeatureProcessor
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def findUnique(_self, feature, attribute):
              naDict = {}
              for na in feature.getAttribute(attribute).split(','):
                  naDict[na] = True
              naString = ""
              for na in naDict.keys():
                  naString += na + ','
              feature.setAttribute(attribute, naString[:-1])
              feature.setAttribute('_count_' + attribute, len(naDict.keys()))

          def input(self,feature):
              self.findUnique(feature, 'code_ar')
              self.findUnique(feature, 'geometry_id')

              self.pyoutput(feature)
          def close(self):
              pass
    -> AttributeSplitter
AttributeSplitter
    TRIM_OPTION = Both
    DELIMITER = ,
    DROP_EMPTY_PARTS = No
    ATTR_NAME = geometry_id
    LIST_NAME = _list_geometry_id
    -> ListExploder
ListExploder
    ATTR_CONFLICT_RES = Use List Attribute Values
    ATTR_ACCUM_MODE = Merge List Attributes
    LIST_ATTR = _list_geometry_id{}
    INDEX_ATTR = _element_index
    ELEMENTS -> FeatureMerger_3 [REQUESTOR]

Bookmark: Calculate area
AreaCalculator
    MULT = 1
    AREA_TYPE = Plane Area
    AREA_ATTR = _area
    -> GeometryRemover_2
    <REJECTED> -> AreaCalculator__Rejected_
AreaCalculator__Rejected_: Logger
    MAXCOORDS = 20
    MESSAGE = Feature is:
    MAXFEATS = 20
GeometryRemover_2
    -> FeatureMerger_3 [SUPPLIER]

Bookmark: Sum area on predecessor
FeatureMerger_3
    IGNORE_NULLS = No
    PROCESS_DUPS = Yes
    MERGE_TYPE = Attributes Only
    SUPPLIERS_FIRST = No
    JOIN_KEYS = @Value(_list_geometry_id) @Value(geometry_id) AUTO
    REJECT_NULL_MISSING_KEYS = No
    ATTR_CONFLICT_RES = Use Requestor
    GEOM_TYPE = Build Polygons
    ATTR_ACCUM_MODE = Merge Supplier
    CONNECT_Z_MODE = First Wins
    MERGED -> Aggregator
Aggregator
    GROUP_BY = predecessor
    SUM = _area
    ORDERED = No
    ACCUM_ATTRS_NAME = Use Attributes From One Feature
    SEP = ,
    MODE = Attributes Only
    AGGREGATE -> JSONTemplater_4 [ROOT]

Bookmark: Write to json
JSONTemplater_4
    VISIBLE_QUERY_VALIDATE = Yes
    ROOT_QUERY_EXPR:
      {
          fme:get-attribute("predecessor"): {
              "area": @int64(@Value("_area")),
              "observedSpecies": fme:get-attribute("_count_code_ar"),
              "areas": fme:get-attribute("_count_geometry_id")
              }
      }
    RESULT_ATTRIBUTE = _result
    -> ListBuilder_2
ListBuilder_2
    GROUPS_ORDERED = No
    LIST_ATTRS_TO_INCLUDE = _result
    LIST_NAME = _list
    -> JSONTemplater_2 [ROOT]
JSONTemplater_2
    VISIBLE_QUERY_VALIDATE = Yes
    ROOT_QUERY_EXPR = [ fme:get-json-list-attribute("_list{}._result") ]
    RESULT_ATTRIBUTE = _result
    -> text_line (writer TEXTLINE_1)
text_line (writer TEXTLINE_1)
    attributes: text_line_data buffer
