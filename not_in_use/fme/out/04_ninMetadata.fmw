FME workspace 04_ninMetadata.fmw

Parameters:
- DestDataset_TEXTLINE_3 = D:\out\json\ninMetadata   # Destination Text File
- DestDataset_TEXTLINE = D:\out\json\ninMetadata\all.json   # Destination Text File
- config_mssql_pass:   # Python Script
      import fme
      import json
      
      data = json.load(open('../../config/mssql.json'))
      
      return data['pass']
- config_mssql_user:   # Python Script
      import fme
      import json
      
      data = json.load(open('../../config/mssql.json'))
      
      return data['user']
- config_mssql_db:   # Python Script
      import fme
      import json
      
      data = json.load(open('../../config/mssql.json'))
      
      return data['db']
- config_mssql_host:   # Python Script
      import fme
      import json
      
      data = json.load(open('../../config/mssql.json'))
      
      return data['host']
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_port:   # Python Script
      import fme
      import json
      
      data = json.load(open('../../config/postgis.json'))
      
      return data['port']
- config_host:   # Python Script
      import fme
      import json
      
      data = json.load(open('../../config/postgis.json'))
      
      return data['host']

Writers:
- TEXTLINE_1: TEXTLINE to $(DestDataset_TEXTLINE_3)
- TEXTLINE_2: TEXTLINE to $(DestDataset_TEXTLINE)

Creator
    GEOMTYPE = Geometry Object
    NUM = 1
    CREATED -> SQLExecutor_3 [INITIATOR]
    CREATED -> SQLExecutor_2 [INITIATOR]
    CREATED -> SQLExecutor_4 [INITIATOR]
    CREATED -> SQLExecutor_5 [INITIATOR] [off]
Note: Remove invalid keys / Prettify
PythonCaller_2
    PYTHONSOURCE:
      # -*- coding: utf-8 -*-
      import fme
      import fmeobjects
      import json
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
      #        codes='codes'
              metadata = json.loads(feature.getAttribute('metadata'))
      #        nyeKoder = []
      #        for koder in metadata[codes]:
      #            if type(koder) is dict:
      #                for kode in koder:
      #                    if kode != "":
      #                        nyeKoder.append(koder[kode])
      #            else:
      #                nyeKoder=metadata[codes][koder]
      #        metadata.pop(codes, None)
      #        if len(nyeKoder) > 0:
      #            metadata[codes] = nyeKoder
              feature.setAttribute('metadata', json.dumps(metadata,  indent=2, ensure_ascii=False))
              self.pyoutput(feature)
          def close(self):
              pass
    PYTHONSYMBOL = FeatureProcessor
    -> text_line (writer TEXTLINE_1)
Note: Remove invalid keys / Prettify
PythonCaller_3
    PYTHONSOURCE:
      # -*- coding: utf-8 -*-
      import fme
      import fmeobjects
      import json
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              #codes='codes'
              metadata = json.loads(feature.getAttribute('metadata'))
              #for lokalid in metadata:
              #    nyeKoder = {}
              #    for koder in metadata[lokalid][codes]:
              #        if type(koder) is dict:
              #            for kode in koder:
              #                if kode != "":
              #                    nyeKoder[kode] = koder[kode]
              #        else:
              #            nyeKoder[koder] = metadata[lokalid][codes][koder]
              #    metadata[lokalid].pop(codes, None)
              #    if len(nyeKoder.keys()) > 0:
              #        metadata[lokalid][codes] = nyeKoder
              feature.setAttribute('metadata', json.dumps(metadata,  indent=2, ensure_ascii=False))
              self.pyoutput(feature)
          def close(self):
              pass
    PYTHONSYMBOL = FeatureProcessor
    -> text_line (writer TEXTLINE_2)

Bookmark: Metadata
Note: Get metadata
SQLExecutor_4
    COMBINE_ATTRS = Result Attributes Only
    COMBINE_GEOM = Initiator Geometry Only
    DATASET = $(config_mssql_db)
    EXPOSED_ATTRIBUTE_LIST = lokalid,brukernavn,naturområdeBeskrivelse,prosjektnavn,prosjektBeskrivelse,programNavn,programBeskrivelse,surveyScale
    FORMAT = MSSQL_ADO
    MSSQL_ADO_COMMAND_TIMEOUT = 30
    MSSQL_ADO_ENCRYPT_CONNECTION = NO
    MSSQL_ADO_PASSWORD = $(config_mssql_pass)
    MSSQL_ADO_QUERY_FEATURE_TYPES_FOR_MERGE_FILTERS = Yes
    MSSQL_ADO_SERVER = $(config_mssql_host)
    MSSQL_ADO_USER_NAME = $(config_mssql_user)
    MSSQL_ADO_USE_SSPI = NO
    SQL_STATEMENT:
      select
      --top 10
      nom.brukernavn,
      nom.lokalid,
      Replace (Replace (REPLACE(nom.beskrivelse,'"',''), CHAR(10), ''), CHAR(13), '') as naturområdeBeskrivelse,
      prj.prosjektnavn,
      Replace (Replace (REPLACE(prj.prosjektbeskrivelse,'"',''), CHAR(10), ''), CHAR(13), '') as prosjektBeskrivelse,
      prg.navn as programNavn,
      Replace (Replace (REPLACE(prg.beskrivelse,'"',''), CHAR(10), ''), CHAR(13), '') as programBeskrivelse,
      nom.kartleggingsMaalestokk as surveyScale
      from
      nin_eier.NATUROMRAADE nom,
      nin_eier.PROSJEKT prj,
      nin_eier.PROGRAM prg
      where
      nom.prosjektFKID = prj.lokalid
      and
      prj.programFKID = prg.lokalid
    RESULT -> FeatureMerger_2 [REQUESTOR]
Note: Get surveyor
SQLExecutor_5
    COMBINE_ATTRS = Result Attributes Only
    COMBINE_GEOM = Initiator Geometry Only
    DATASET = $(config_mssql_db)
    EXPOSED_ATTRIBUTE_LIST = brukernavn,firma,email,hjemmeside,navn
    FORMAT = MSSQL_ADO
    MSSQL_ADO_COMMAND_TIMEOUT = 30
    MSSQL_ADO_ENCRYPT_CONNECTION = NO
    MSSQL_ADO_PASSWORD = $(config_mssql_pass)
    MSSQL_ADO_QUERY_FEATURE_TYPES_FOR_MERGE_FILTERS = Yes
    MSSQL_ADO_SERVER = $(config_mssql_host)
    MSSQL_ADO_USER_NAME = $(config_mssql_user)
    MSSQL_ADO_USE_SSPI = NO
    SQL_STATEMENT:
      select
      --top 10
      b.navn,
      b.brukernavn,
      b.firmaNavn as firma,
      b.email,
      b.hjemmeside
      from
      nin_eier.BRUKER b
    RESULT -> FeatureMerger_2 [SUPPLIER]
FeatureMerger_2
    ATTR_ACCUM_MODE = Merge Supplier
    ATTR_CONFLICT_RES = Use Requestor
    CLEANING_TOLERANCE = None
    IGNORE_NULLS = No
    JOIN_KEYS = @Value(brukernavn) @Value(brukernavn) STRING
    MERGE_TYPE = Attributes Only
    PROCESS_DUPS = No
    REJECT_NULL_MISSING_KEYS = No
    SUPPLIERS_FIRST = No
    MERGED -> FeatureMerger [REQUESTOR]
    UNMERGED_REQUESTOR -> FeatureMerger [REQUESTOR]

Bookmark: Natruområdetype
Note: Get naturområdetype
SQLExecutor_2
    COMBINE_ATTRS = Result Attributes Only
    COMBINE_GEOM = Initiator Geometry Only
    DATASET = $(config_mssql_db)
    EXPOSED_ATTRIBUTE_LIST = kode,naturområdetypeLokalid,andel,lokalid
    FORMAT = MSSQL_ADO
    MSSQL_ADO_COMMAND_TIMEOUT = 30
    MSSQL_ADO_ENCRYPT_CONNECTION = NO
    MSSQL_ADO_PASSWORD = $(config_mssql_pass)
    MSSQL_ADO_QUERY_FEATURE_TYPES_FOR_MERGE_FILTERS = Yes
    MSSQL_ADO_SERVER = $(config_mssql_host)
    MSSQL_ADO_USER_NAME = $(config_mssql_user)
    MSSQL_ADO_USE_SSPI = NO
    SQL_STATEMENT:
      select
      nat.naturomraadeFKID as lokalid,
      nat.lokalid as naturområdetypeLokalid,
      nat.kode,
      nat.andel
      from
      nin_eier.NATUROMRAADETYPE nat

      --where nat.naturomraadeFKID = '11E90AB5-A737-4458-BE82-31CB61B71927'
    RESULT -> StringReplacer_3
StringReplacer_3
    CASE = NO
    FIND_TEXT = _
    NO_MATCH = _FME_NO_OP_
    REGEXP = NO
    REPLACE_TEXT = -
    SRC_ATTRS = kode
    -> AttributeFilter_2
AttributeFilter_2
    ATTR_NAME = andel
    ATTR_VALUES = <Empty>,<Missing>,<Null>,<Unfiltered>
    <EMPTY> -> AttributeManager
    <MISSING> -> AttributeManager
    <NULL> -> AttributeManager
    <UNFILTERED> -> AttributeFilter
AttributeManager
    ATTR_TABLE = SET_TO andel = 10
    -> AttributeFilter
AttributeFilter
    ATTR_NAME = kode
    ATTR_VALUES = <Empty>,<Missing>,<Null>,<Unfiltered>
    <EMPTY> -> AttributeFilter__Empty_
    <MISSING> -> AttributeFilter__Empty_
    <NULL> -> AttributeFilter__Empty_
    <UNFILTERED> -> AttributeTrimmer
AttributeTrimmer
    SRC_ATTRS = kode
    TRIM_CHARS = " "
    TRIM_TO_NONE = Yes
    TRIM_TYPE = Both
    -> SQLExecutor_8 [INITIATOR]
    -> AttributeTrimmer_Output
SQLExecutor_8
    COMBINE_ATTRS = Keep Result Attributes if Conflict
    COMBINE_GEOM = Initiator Geometry Only
    DATASET = $(config_db)
    EXPOSED_ATTRIBUTE_LIST = tittel
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_READ_TIME_WITH_TIMEZONE = Yes
    POSTGRES_USER_NAME = $(config_user)
    SQL_STATEMENT:
      select c.title as tittel
      from
      data.codes c
      where
      c.code = '@Value(kode)'
    RESULT -> JSONTemplater_3 [ROOT]
AttributeTrimmer_Output: Inspector
AttributeFilter__Empty_: Logger
    MAXCOORDS = 20
    MAXFEATS = 20
    MESSAGE = Feature is:

Bookmark: Beskrivelsesvariabler
Note: Get beskrivelsesvariabler / Filters out those that ends in '-x' and '-XY' / Filters out variabelGruppe 'Mdir' and 'uLKM'
SQLExecutor_3
    COMBINE_ATTRS = Result Attributes Only
    COMBINE_GEOM = Initiator Geometry Only
    DATASET = $(config_mssql_db)
    EXPOSED_ATTRIBUTE_LIST = naturområdetypeLokalid,variabelGruppe,variabelTema,variabelNavn,variabelTrinn
    FORMAT = MSSQL_ADO
    MSSQL_ADO_COMMAND_TIMEOUT = 30
    MSSQL_ADO_ENCRYPT_CONNECTION = NO
    MSSQL_ADO_MULTI_SUBNET_FAILOVER = NO
    MSSQL_ADO_PASSWORD = $(config_mssql_pass)
    MSSQL_ADO_QUERY_FEATURE_TYPES_FOR_MERGE_FILTERS = Yes
    MSSQL_ADO_SERVER = $(config_mssql_host)
    MSSQL_ADO_USER_NAME = $(config_mssql_user)
    MSSQL_ADO_USE_SSPI = NO
    SQL_STATEMENT:
      select --top 10000
      bv.omraadetypeFKID as naturområdetypeLokalid,
      --bv.kode as beskrivelsesvariabel,
      bv.variabelGruppe,
      bv.variabelTema,
      bv.variabelNavn,
      bv.variabelTrinn
      from
      nin_eier.BESKRIVELSESVARIABEL bv
      where
      bv.kode not like '%-XY'
      and
      bv.kode not like '%-x'
      and
      bv.variabelGruppe not in ('Mdir', 'uLKM')
    RESULT -> AttributeFilter_3
AttributeFilter_3
    ATTR_NAME = variabelNavn
    ATTR_VALUES = <Empty>,<Missing>,<Null>,<Unfiltered>
    <EMPTY> -> AttributeCreator_2
    <MISSING> -> AttributeCreator_2
    <NULL> -> AttributeCreator_2
    <UNFILTERED> -> AttributeCreator
AttributeCreator_2
    ATTR_TABLE:
      SET_TO beskrivelsesvariabel = NA-BS-@Value(variabelGruppe)@Value(variabelTema)
      SET_TO parentCode = NA-BS-@Value(variabelGruppe)
    -> AttributeFilter_5
AttributeCreator
    ATTR_TABLE:
      SET_TO beskrivelsesvariabel = NA-BS-@Value(variabelGruppe)@Value(variabelTema)-@Value(variabelNavn)
      SET_TO parentCode = NA-BS-@Value(variabelGruppe)@Value(variabelTema)-@Value(variabelNavn)
    -> AttributeFilter_5
AttributeFilter_5
    ATTR_NAME = variabelTrinn
    ATTR_VALUES = <Empty>,<Missing>,<Null>,<Unfiltered>
    <EMPTY> -> SQLExecutor_9 [INITIATOR]
    <MISSING> -> SQLExecutor_9 [INITIATOR]
    <NULL> -> SQLExecutor_9 [INITIATOR]
    <UNFILTERED> -> AttributeCreator_4
AttributeCreator_4
    ATTR_TABLE = SET_TO beskrivelsesvariabel = @Value(beskrivelsesvariabel)-@Value(variabelTrinn)
    -> SQLExecutor_9 [INITIATOR]
SQLExecutor_9
    COMBINE_ATTRS = Keep Result Attributes if Conflict
    COMBINE_GEOM = Initiator Geometry Only
    DATASET = $(config_db)
    EXPOSED_ATTRIBUTE_LIST = tittel
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_USER_NAME = $(config_user)
    SQL_STATEMENT:
      select c.title as tittel
      from
      data.codes c
      where
      c.code = '@Value(beskrivelsesvariabel)'
    RESULT -> AttributeFilter_4
Note: Find codes that need an explanation
PythonCaller_4
    NEW_ATTRIBUTES = parentCode
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              code = feature.getAttribute('beskrivelsesvariabel')
              if(len(code.split("_")) < 3):
                  feature.setAttribute('parentCode', None)
                  self.pyoutput(feature)
              else:
                  parentCode = code.split("_")[0] + '_' + code.split("_")[1]
                  feature.setAttribute('parentCode', parentCode)
                  self.pyoutput(feature)
          def close(self):
              pass
    PYTHONSYMBOL = FeatureProcessor
    -> AttributeFilter_4
AttributeFilter_4
    ATTR_NAME = parentCode
    ATTR_VALUES = <Empty>,<Missing>,<Null>,<Unfiltered>
    <EMPTY> -> JSONTemplater_5 [ROOT]
    <EMPTY> -> AttributeFilter_4__Empty_
    <UNFILTERED> -> SQLExecutor_10 [INITIATOR]
SQLExecutor_10
    COMBINE_ATTRS = Keep Result Attributes if Conflict
    COMBINE_GEOM = Initiator Geometry Only
    DATASET = $(config_db)
    EXPOSED_ATTRIBUTE_LIST = parent
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_USER_NAME = $(config_user)
    SQL_STATEMENT:
      select
      c.title as parent
      from
      data.codes c
      where
      c.code = '@Value(parentCode)'
    RESULT -> JSONTemplater_4 [ROOT]
JSONTemplater_4
    CONSECUTIVE_GROUPS = No
    GROUP_BY = naturområdetypeLokalid
    RESULT_ATTRIBUTE = beskrivelsesvariabler
    ROOT_QUERY_EXPR:
      {
          fme:get-attribute("beskrivelsesvariabel"): {
              "tittel": fme:get-attribute("tittel"),
              "forfader": fme:get-attribute("parent")
              }
      }
    VISIBLE_QUERY_VALIDATE = Yes
    -> ListBuilder_2
JSONTemplater_5
    CONSECUTIVE_GROUPS = No
    GROUP_BY = naturområdetypeLokalid
    RESULT_ATTRIBUTE = beskrivelsesvariabler
    ROOT_QUERY_EXPR:
      {
          fme:get-attribute("beskrivelsesvariabel"): {
              "tittel": fme:get-attribute("tittel")
              }
      }
    VISIBLE_QUERY_VALIDATE = Yes
    -> ListBuilder_2
ListBuilder_2
    GROUPS_ORDERED = No
    GROUP_BY = naturområdetypeLokalid
    LIST_ATTRS_TO_INCLUDE = beskrivelsesvariabler
    LIST_NAME = _list
    -> JSONTemplater_3 [KODER]
AttributeFilter_4__Empty_: Inspector

Bookmark: Join beskrivelsesvariabler with naturområdetyper
JSONTemplater_3
    CONSECUTIVE_GROUPS = No
    GROUP_BY = naturområdetypeLokalid
    KODER_QUERY_EXPR = {fme:get-json-list-attribute("_list{}.beskrivelsesvariabler")}
    RESULT_ATTRIBUTE = koder
    ROOT_QUERY_EXPR:
      {
          fme:get-attribute("kode"): {
              "andel": fme:get-attribute("andel"),
              "tittel": fme:get-attribute("tittel"),
              "beskrivelsesvariabler": fme:process-features("KODER")
          }
      }
    VISIBLE_QUERY_VALIDATE = Yes
    -> ListBuilder_3
ListBuilder_3
    GROUPS_ORDERED = No
    GROUP_BY = lokalid
    LIST_ATTRS_TO_INCLUDE = koder naturområdetypeLokalid
    LIST_NAME = koder_list
    -> FeatureMerger [SUPPLIER]

Bookmark: Join all data and minor tidying
FeatureMerger
    ATTR_ACCUM_MODE = Merge Supplier
    ATTR_CONFLICT_RES = Use Requestor
    CLEANING_TOLERANCE = None
    IGNORE_NULLS = No
    JOIN_KEYS = @Value(lokalid) @Value(lokalid) AUTO
    MERGE_TYPE = Attributes Only
    PROCESS_DUPS = No
    REJECT_NULL_MISSING_KEYS = No
    SUPPLIERS_FIRST = No
    MERGED -> StringReplacer
    UNMERGED_REQUESTOR -> FeatureMerger_UnmergedRequestor
    UNUSED_SUPPLIER -> FeatureMerger_UnmergedRequestor
StringReplacer
    CASE = NO
    FIND_TEXT = {
    NO_MATCH = _FME_NO_OP_
    REGEXP = NO
    SRC_ATTRS = lokalid
    -> StringReplacer_2
StringReplacer_2
    CASE = NO
    FIND_TEXT = }
    NO_MATCH = _FME_NO_OP_
    REGEXP = NO
    SRC_ATTRS = lokalid
    -> AttributeValueMapper
Note: SurveyScale is just guessed here
AttributeValueMapper
    DIRECTION = Forward (Source To Destination)
    LUT = 3,1:5000,FME_NULL_VALUE,ukjent
    SRC = surveyScale
    VAL_ATTR = surveyScale
    -> JSONTemplater_6 [SUB]
    -> JSONTemplater_6 [ROOT]
Note: Build JSON per lokalid / Adds hardcoded owner
JSONTemplater_6
    CONSECUTIVE_GROUPS = No
    GROUP_BY = koder_list{0}.naturområdetypeLokalid
    RESULT_ATTRIBUTE = metadata
    ROOT_QUERY_EXPR:
      {
          "description": fme:get-attribute("naturområdeBeskrivelse"),
          "surveyer": {
              "company": fme:get-attribute("firma"),
              "contactPerson" : fme:get-attribute("navn"),
              "email": fme:get-attribute("email"),
              "homepage": fme:get-attribute("hjemmeside")
          },
         "owner": {
              "company": "Miljødirektoratet",
              "contactPerson": "kjepet (Kjetil Pettersson)",
              "email": "kjetil.pettersson@miljodir.no",
              "homepage": "http://www.miljodirektoratet.no"
          },
          "program": {
              "name": fme:get-attribute("programNavn"),
              "description":  fme:get-attribute("programBeskrivelse")
          },
          "project":{
              "name": fme:get-attribute("prosjektnavn"),
              "description":  fme:get-attribute("prosjektBeskrivelse")
          },
          "surveyScale": fme:get-attribute("surveyScale"),
          "codes": fme:process-features("SUB")
      }
    SUB_QUERY_EXPR = {fme:get-json-list-attribute("koder_list{}.koder")}
    VISIBLE_QUERY_VALIDATE = Yes
    -> PythonCaller_2 [off]
    -> JSONTemplater [ROOT]
    -> text_line (writer TEXTLINE_1)
FeatureMerger_UnmergedRequestor: Logger
    MAXCOORDS = 20
    MAXFEATS = 20
    MESSAGE = Feature is:

Bookmark: Individual json pr naturområde
text_line (writer TEXTLINE_1)
    attributes: text_line_data buffer

Bookmark: Single json-file
Note: Adds localid-key
JSONTemplater
    RESULT_ATTRIBUTE = metadata
    ROOT_QUERY_EXPR:
      {fme:get-attribute("lokalid"):
          fme:get-json-attribute("metadata")
      }
    VISIBLE_QUERY_VALIDATE = Yes
    -> ListBuilder
ListBuilder
    GROUPS_ORDERED = No
    LIST_ATTRS_TO_INCLUDE = lokalid metadata
    LIST_NAME = _list
    -> JSONTemplater_2 [ROOT]
Note: Merge all JSON to one file
JSONTemplater_2
    RESULT_ATTRIBUTE = text_line_data
    ROOT_QUERY_EXPR = {[fme:get-json-list-attribute("_list{}.metadata")]}
    VISIBLE_QUERY_VALIDATE = Yes
    -> PythonCaller_3 [off]
    -> text_line (writer TEXTLINE_2)
text_line (writer TEXTLINE_2)
    attributes: text_line_data buffer
