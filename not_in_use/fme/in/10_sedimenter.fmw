FME workspace 10_sedimenter.fmw

Parameters:
- SourceDataset_FILEGDB = D:\in\NGU\Sediment_NiN.gdb   # File Geodatabase
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_port:   # Python Script
      import fme
      import json
      
      data = json.load(open('../../config/postgis.json'))
      
      return data['port']
- config_host:   # Python Script
      import fme
      import json
      
      data = json.load(open('../../config/postgis.json'))
      
      return data['host']
- Dataset = sedimenter
- Prefix = NA-LKM
- PrefixDesc = Sedimenter

Readers:
- FILEGDB_1: FILEGDB from $(SourceDataset_FILEGDB)

Writers:
- POSTGIS_1: POSTGIS to $(config_db)

Kornstorrelse_S3E_S3F_Det (reader FILEGDB_1)
    attributes: OBJECTID objectid, OBJTYPE text(32), DATO date, SUBTYPEKODE text(18), MREF int, FTEMA int, SEDKORNSTR text(55), GRAVBARHET text(22), Shape_Length double, Shape_Area double, S3E text(5), S3F text(5), Areal double, AREAL_p_KL double
    -> Clipper [CLIPPER]
    -> AttributeKeeper_2
Kornstorrelse_S3E_S3F_Reg (reader FILEGDB_1)
    attributes: OBJECTID objectid, OBJTYPE text(32), DATO date, SUBTYPEKODE text(18), MREF int, FTEMA int, SEDKORNSTR text(55), Shape_Length double, Shape_Area double, S3E text(5), S3F text(5), Areal double, AEREAL_p_KL double
    -> Clipper [CLIPPEE]
Clipper
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clippee Only
    OUTSIDE -> AttributeKeeper_2
AttributeKeeper_2
    KEEP_ATTRS = S3E,S3F
    -> Sampler
Sampler
    RATE = 1
    SAMPLE_MODE = No
    SAMPLE_TYPE_LONG = First N Features
    SAMPLED -> SQLExecutor_4 [INITIATOR]
    NOT_SAMPLED -> Reprojector
Note: Insert dataset
SQLExecutor_4
    COMBINE_ATTRS = Keep Result Attributes if Conflict
    COMBINE_GEOM = Initiator Geometry Only
    DATASET = $(config_db)
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_READ_TIME_WITH_TIMEZONE = Yes
    POSTGRES_SCHEMAS_FOR_TABLE_LISTING = data
    POSTGRES_USER_NAME = $(config_user)
    SQL_STATEMENT:
      DELETE FROM data.dataset WHERE description='$(Dataset)';
      INSERT INTO data.prefix (value, description) values ('$(Prefix)', '$(PrefixDesc)') ON CONFLICT DO NOTHING;
      COMMIT;
      INSERT INTO data.dataset (prefix_id, description) Select id, '$(Dataset)' from data.prefix where value = '$(Prefix)' and description = '$(PrefixDesc)';
    INITIATOR -> Reprojector
Reprojector
    DEST = EPSG:4326
    INTERPOLATION_TYPE_NAME = Nearest Neighbor
    RASTER_CELL_SIZE = Preserve Cells
    RASTER_TOLERANCE = 0.0
    SOURCE = Read from feature
    REPROJECTED -> SQLExecutor_2 [INITIATOR]
Note: Get id for pk
SQLExecutor_2
    COMBINE_ATTRS = Keep Initiator Attributes if Conflict
    COMBINE_GEOM = Initiator Geometry Only
    DATASET = $(config_db)
    EXPOSED_ATTRIBUTE_LIST = id
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_SCHEMAS_FOR_TABLE_LISTING = data
    POSTGRES_USER_NAME = $(config_user)
    SQL_STATEMENT = SELECT nextval('data.geometry_id_seq') as id
    RESULT -> SQLExecutor [INITIATOR]
    RESULT -> AttributeRenamer_4
AttributeRenamer_4
    ATTR_TABLE:
      RENAME_SET_DEFAULT id > geometry_id
      RENAME_SET_DEFAULT oppdateringsdato > created
    -> AttributeValueMapper
    -> AttributeValueMapper_2
AttributeValueMapper
    DIRECTION = Forward (Source To Destination)
    LUT = 0,0,1,a,2,b,4,c,3,d,5,e,6,f,7,+
    SRC = S3E
    VAL_ATTR = S3E_mapped
    -> AttributeFilter
AttributeFilter
    ATTR_NAME = S3E_mapped
    ATTR_VALUES = <Empty>,<Missing>,<Null>,<Unfiltered>
    <EMPTY> -> AttributeCreator_2
    <UNFILTERED> -> AttributeRenamer_2
AttributeRenamer_2
    ATTR_TABLE = RENAME_SET_DEFAULT S3E_mapped > S3E
    -> AttributeCreator_2
AttributeCreator_2
    ATTR_TABLE = SET_TO code = $(Prefix)-S3-E-@Value(S3E)
    -> SQLExecutor_5 [INITIATOR]
AttributeValueMapper_2
    DIRECTION = Forward (Source To Destination)
    LUT = Ø,¤
    SRC = S3F
    VAL_ATTR = S3F_mapped
    -> AttributeFilter_2
AttributeFilter_2
    ATTR_NAME = S3F_mapped
    ATTR_VALUES = <Empty>,<Missing>,<Null>,<Unfiltered>
    <EMPTY> -> AttributeCreator
    <UNFILTERED> -> AttributeRenamer
AttributeRenamer
    ATTR_TABLE = RENAME_SET_DEFAULT S3F_mapped > S3F
    -> AttributeCreator
AttributeCreator
    ATTR_TABLE = SET_TO code = $(Prefix)-S3-F-@Value(S3F)
    -> SQLExecutor_5 [INITIATOR]
Note: Get code-id
SQLExecutor_5
    COMBINE_ATTRS = Keep Result Attributes if Conflict
    COMBINE_GEOM = Initiator Geometry Only
    DATASET = $(config_db)
    EXPOSED_ATTRIBUTE_LIST = codes_id
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_SCHEMAS_FOR_TABLE_LISTING = data
    POSTGRES_USER_NAME = $(config_user)
    SQL_STATEMENT = select id as codes_id from data.codes where code = '@Value(code)';
    RESULT -> codes_geometry (writer POSTGIS_1)
codes_geometry (writer POSTGIS_1)
    attributes: codes_id text, geometry_id text, code text, created timestamp
Note: Get dataset id
SQLExecutor
    COMBINE_ATTRS = Keep Initiator Attributes if Conflict
    COMBINE_GEOM = Initiator Geometry Only
    DATASET = bigbadabom
    EXPOSED_ATTRIBUTE_LIST = dataset_id
    FORMAT = POSTGRES
    POSTGRES_HOST = localhost
    POSTGRES_PASSWORD =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
    POSTGRES_PORT = 5432
    POSTGRES_QUERY_FEATURE_TYPES_FOR_MERGE_FILTERS = Yes
    POSTGRES_READ_TIME_WITH_TIMEZONE = Yes
    POSTGRES_SCHEMAS_FOR_TABLE_LISTING = data
    POSTGRES_USER_NAME = postgres
    SQL_STATEMENT = select id as dataset_id from data.dataset where description='$(Dataset)';
    RESULT -> geometry (writer POSTGIS_1)
geometry (writer POSTGIS_1)
    attributes: dataset_id int8, id int8
