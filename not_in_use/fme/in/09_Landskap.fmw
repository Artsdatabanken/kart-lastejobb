FME workspace 09_Landskap.fmw

Parameters:
- SourceDataset_ESRISHAPE = D:\in\Landskap\NiN_LA_komplett.shp   # Source Esri Shapefile(s)
- SourceDataset_ESRISHAPE_3 = D:\in\Landskap\NiN-LA_marint.shp   # Source Esri Shapefile(s)
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_port:   # Python Script
      import fme
      import json
      
      data = json.load(open('../../config/postgis.json'))
      
      return data['port']
- config_host:   # Python Script
      import fme
      import json
      
      data = json.load(open('../../config/postgis.json'))
      
      return data['host']
- Dataset = landskap
- Prefix = LA
- PrefixDesc = Landskap

Readers:
- ESRISHAPE_2: ESRISHAPE from $(SourceDataset_ESRISHAPE)
- ESRISHAPE_1: ESRISHAPE from $(SourceDataset_ESRISHAPE_3)

Writers:
- POSTGIS_1: POSTGIS to $(config_db)

NiN_LA_komplett (reader ESRISHAPE_2)
    attributes: gridcode long, Shape_Leng double, N_sys_niva char(254), HTG char(254), GT char(254), Gridkode char(254), S_kode char(254), HT char(254), Shape_Le_1 double, Shape_Area double
    -> AttributeCreator
AttributeCreator
    ATTR_TABLE = SET_TO code = $(Prefix)-@Value(HTG)-@Value(HT)-@Value(GT)
    -> AttributeKeeper
AttributeKeeper
    KEEP_ATTRS = code
    -> Sampler
NiN-LA_marint (reader ESRISHAPE_1)
    attributes: FID_Basin_ long, OBJECTID long, Id long, gridcode long, Shape_Leng double, ORIG_FID long, FID_Basin1 long, FID_Basi_1 long, FID_Bredef long, Shape_Le_1 double, Shape_Area double, NiN_kode char(254)
    -> AttributeCreator_2
AttributeCreator_2
    ATTR_TABLE = SET_TO code = @Substring(@Value(NiN_kode),0,@StringLength(@Value(NiN_kode)) - 1)-@Substring(@Value(NiN_kode),-1,1)
    -> AttributeKeeper_2
AttributeKeeper_2
    KEEP_ATTRS = code
    -> Sampler
Sampler
    RATE = 1
    SAMPLE_MODE = No
    SAMPLE_TYPE_LONG = First N Features
    SAMPLED -> SQLExecutor_4 [INITIATOR]
    NOT_SAMPLED -> Reprojector
Note: Insert dataset / (prefix should already be there from NiN-import)
SQLExecutor_4
    COMBINE_ATTRS = Keep Initiator Attributes if Conflict
    COMBINE_GEOM = Initiator Geometry Only
    DATASET = $(config_db)
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_SCHEMAS_FOR_TABLE_LISTING = data
    POSTGRES_USER_NAME = $(config_user)
    SQL_STATEMENT:
      DELETE FROM data.dataset WHERE description='$(Dataset)';
      INSERT INTO data.prefix (value, description) values ('$(Prefix)', '$(PrefixDesc)') ON CONFLICT DO NOTHING;
      COMMIT;
      INSERT INTO data.dataset (prefix_id, description) Select id, '$(Dataset)' from data.prefix where value = '$(Prefix)';
    INITIATOR -> Reprojector
Reprojector
    DEST = EPSG:4326
    INTERPOLATION_TYPE_NAME = Nearest Neighbor
    RASTER_CELL_SIZE = Preserve Cells
    RASTER_TOLERANCE = 0.0
    SOURCE = Read from feature
    REPROJECTED -> Deaggregator
Deaggregator
    EXPLODE_INSTANCES = Yes
    GEOM_NAME_FIELD = _geometry_name
    LIST_ATTR_MODE_LOOKUP = LEAN
    MODE = Flatten All Levels
    SPLIT_COMPOSITES = No
    DEAGGREGATED -> SQLExecutor_2 [INITIATOR]
Note: Get id for pk
SQLExecutor_2
    COMBINE_ATTRS = Keep Initiator Attributes if Conflict
    COMBINE_GEOM = Initiator Geometry Only
    DATASET = $(config_db)
    EXPOSED_ATTRIBUTE_LIST = id
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_SCHEMAS_FOR_TABLE_LISTING = data
    POSTGRES_USER_NAME = $(config_user)
    SQL_STATEMENT = SELECT nextval('data.geometry_id_seq') as id
    RESULT -> SQLExecutor [INITIATOR]
    RESULT -> AttributeRenamer_4
AttributeRenamer_4
    ATTR_TABLE:
      RENAME_SET_DEFAULT id > geometry_id
      RENAME_SET_DEFAULT oppdateringsdato > created
    -> SQLExecutor_5 [INITIATOR]
Note: Get code-id
SQLExecutor_5
    COMBINE_ATTRS = Keep Result Attributes if Conflict
    COMBINE_GEOM = Initiator Geometry Only
    DATASET = $(config_db)
    EXPOSED_ATTRIBUTE_LIST = codes_id
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_SCHEMAS_FOR_TABLE_LISTING = data
    POSTGRES_USER_NAME = $(config_user)
    SQL_STATEMENT = select id as codes_id from data.codes where code = '@Value(code)';
    RESULT -> codes_geometry (writer POSTGIS_1)
codes_geometry (writer POSTGIS_1)
    attributes: codes_id text, geometry_id text, code text, created timestamp
Note: Get dataset id
SQLExecutor
    COMBINE_ATTRS = Keep Initiator Attributes if Conflict
    COMBINE_GEOM = Initiator Geometry Only
    DATASET = bigbadabom
    EXPOSED_ATTRIBUTE_LIST = dataset_id
    FORMAT = POSTGRES
    POSTGRES_HOST = localhost
    POSTGRES_PASSWORD =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
    POSTGRES_PORT = 5432
    POSTGRES_QUERY_FEATURE_TYPES_FOR_MERGE_FILTERS = Yes
    POSTGRES_SCHEMAS_FOR_TABLE_LISTING = data
    POSTGRES_USER_NAME = postgres
    SQL_STATEMENT = select id as dataset_id from data.dataset where description='$(Dataset)';
    RESULT -> geometry (writer POSTGIS_1)
geometry (writer POSTGIS_1)
    attributes: dataset_id int8, id int8
