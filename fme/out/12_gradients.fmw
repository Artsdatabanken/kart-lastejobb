FME workspace 12_gradients.fmw

Parameters:
- SourceDataset_GEOTIFF = ""D:\in\Landskap\LA_raster\KLG_AI_k.tif" "D:\in\Landskap\LA_raster\KLG_JP_k.tif" "D:\in\Landskap\LA_raster\KLG_KA_k.tif" "D:\in\Landskap\LA_raster\KLG_VP_k.tif""   # Source GeoTIFF File(s)
- DestDataset_PNGRASTER = D:\out\codecube   # Destination PNG (Portable Network Graphics) Folder
- SourceDataset_GEOTIFF_3 = ""D:\in\Landskap\LA_raster\KLG_BP_d.tif" "D:\in\Landskap\LA_raster\KLG_IP_d.tif" "D:\in\Landskap\LA_raster\KLG_IYK_d.tif" "D:\in\Landskap\LA_raster\KLG_JA_d.tif" "D:\in\Landskap\LA_raster\KLG_RE_IA_d.tif" "D:\in\Landskap\LA_raster\KLG_RE_KF_ID_d.tif" "D:\in\Landskap\LA_raster\KLG_RE_KS_d.tif" "D:\in\Landskap\LA_raster\KLG_VE_d.tif" "D:\in\Landskap\LA_raster\KLG_VP_d.tif""   # Source GeoTIFF File(s)
- DestDataset_TEXTLINE = D:\out\codecube   # Destination Text File

Readers:
- GEOTIFF_1: GEOTIFF from $(SourceDataset_GEOTIFF)
- GEOTIFF_2: GEOTIFF from $(SourceDataset_GEOTIFF_3)

Writers:
- PNGRASTER_1: PNGRASTER to $(DestDataset_PNGRASTER)
- TEXTLINE_1: TEXTLINE to $(DestDataset_TEXTLINE)

raster.data.8bit.3857 (writer PNGRASTER_1)
    attributes: min char(200), max char(200), range char(200), type char(200), bitdepth char(200), code char(200), datatype char(255), _band{}_min char(200), _band{}_max char(200), _band{}_palette{}_keyMin char(200), _band{}_palette{}_keyMax char(200), _band{}_palette{}_valueMin char(200), _band{}_palette{}_valueMax char(200)

Bookmark: Classes
GEOTIFF (reader GEOTIFF_2)
    attributes: datatype char(255)
    -> AttributeCreator_3
AttributeCreator_3
    ATTR_TABLE:
      SET_TO type = classes
      SET_TO bitdepth = 8
      SET_TO code = @ReplaceString(@ReplaceString(LA_@Value(fme_basename),_k,""),_,\)
    -> RasterInterpretationCoercer
RasterInterpretationCoercer
    COLOR_TO_COLOR = Scale by data type
    FLOAT_TO_INTEGER = Round
    INTERPRETATION = Gray8
    NUMERIC_TO_COLOR = Scale by data values
    -> Reprojector_2
Note: Use nearest for classes
Reprojector_2
    DEST = EPSG:3857
    INTERPOLATION_TYPE_NAME = Nearest Neighbor
    RASTER_CELL_SIZE = Preserve Cells
    RASTER_TOLERANCE = 0.0
    SOURCE = EPSG:25833
    REPROJECTED -> raster.data.8bit.3857 (writer PNGRASTER_1)

Bookmark: Data
GEOTIFF (reader GEOTIFF_1)
    attributes: datatype char(255)
    -> AttributeCreator_4
AttributeCreator_4
    ATTR_TABLE:
      SET_TO type = data
      SET_TO bitdepth = 16bit
      SET_TO code = @ReplaceString(@ReplaceString(LA_@Value(fme_basename),_k,""),_,\)
    -> RasterBandMinMaxExtractor
RasterBandMinMaxExtractor
    -> AttributeCreator
AttributeCreator
    ATTR_TABLE:
      SET_TO min = @double(@Value(_band{0}.min))
      SET_TO max = @double(@Value(_band{0}.max))
      SET_TO range = @double(@Value(_band{0}.max)-@Value(_band{0}.min))
    -> RasterExpressionEvaluator_3 [A]
    -> JSONTemplater [ROOT]
RasterExpressionEvaluator_3
    EXPRESSION_LIST = INTERPRETATION_LIST "GRAY16" EXPRESSION_LIST "@uint16(((A[0]-@Value(A:min))/@Value(A:range))*65534)"
    MODE = One Raster
    RESULT -> Reprojector
Note: Use bilinear interp for data
Reprojector
    DEST = EPSG:3857
    INTERPOLATION_TYPE_NAME = Bilinear
    RASTER_CELL_SIZE = Preserve Cells
    RASTER_TOLERANCE = 0.0
    SOURCE = EPSG:25833
    REPROJECTED -> raster.data.8bit.3857 (writer PNGRASTER_1)
JSONTemplater
    RESULT_ATTRIBUTE = text_line_data
    ROOT_QUERY_EXPR:
      {
        "value_range": {
          "source": [ fme:get-attribute("min"),  fme:get-attribute("max") ],
          "compressed": [0,65534],
          "nodata": 65535
        }
      }
    VISIBLE_QUERY_VALIDATE = Yes
    -> text_line (writer TEXTLINE_1)
text_line (writer TEXTLINE_1)
    attributes: text_line_data buffer
