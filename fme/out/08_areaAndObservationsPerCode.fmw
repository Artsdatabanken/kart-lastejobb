FME workspace 08_areaAndObservationsPerCode.fmw

Parameters:
- DestDataset_TEXTLINE = D:\out\json\codes\areasAndObservationsPerCode.json   # Destination Text File
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_port:   # Python Script
      import fme
      import json
      
      data = json.load(open('../../config/postgis.json'))
      
      return data['port']
- config_host:   # Python Script
      import fme
      import json
      
      data = json.load(open('../../config/postgis.json'))
      
      return data['host']

Writers:
- TEXTLINE_1: TEXTLINE to $(DestDataset_TEXTLINE)

Note: Skip species-test for now. / Level seems to be inconsistent, species level is not always the same. / Keeping this for future implementation.
Creator
    GEOMTYPE = Geometry Object
    NUM = 1
    CREATED -> AttributeCreator
    CREATED -> SQLExecutor [INITIATOR]

Bookmark: Datasets
SQLExecutor
    SQL_STATEMENT:
      select
      d.id as dataset_id, p.value as prefix
      from
      data.dataset d, data.prefix p
      where
      d.prefix_id = p.id
    POSTGRES_HOST = $(config_host)
    COMBINE_ATTRS = Result Attributes Only
    POSTGRES_QUERY_FEATURE_TYPES_FOR_MERGE_FILTERS = Yes
    DATASET = $(config_db)
    COMBINE_GEOM = Initiator Geometry Only
    POSTGRES_PORT = 5432
    POSTGRES_PASSWORD = $(config_pass)
    POSTGRES_USER_NAME = $(config_user)
    FORMAT = POSTGRES
    EXPOSED_ATTRIBUTE_LIST = dataset_id,prefix
    RESULT -> AttributeFilter
AttributeFilter
    ATTR_VALUES = <Empty>,<Missing>,<Null>,<Unfiltered>,AR
    ATTR_NAME = prefix
    <UNFILTERED> -> FeatureMerger [SUPPLIER]
    AR -> FeatureMerger_2 [SUPPLIER]

Bookmark: Geometries
AttributeCreator
    ATTR_TABLE = SET_TO id
    -> FeatureReader [INITIATOR]
FeatureReader
    FORMAT = POSTGIS
    FEATURETYPES = data.geometry
    POSTGIS_USE_TRUE_POSTGIS_TYPES = yes
    POSTGIS_HOST = $(config_host)
    OUTPUT_FEATURES_DISPLAY = Schema and Data Features
    POSTGIS_DISABLE_COLLECTION_SPLITTING = yes
    POSTGIS_PORT = $(config_port)
    POSTGIS_POSTGIS_EXPOSE_FORMAT_ATTRS = postgres_oid,int4
    POSTGIS_FEATURES_PER_FETCH = 10000
    POSTGIS_USE_SEARCH_ENVELOPE = NO
    POSTGIS_QUERY_FEATURE_TYPES_FOR_MERGE_FILTERS = Yes
    INTERACT = <No Spatial Filter>
    ATTR_ACCUM_MODE = Merge Initiator and Result
    DATASET = $(config_db)
    POSTGIS_USER_NAME = $(config_user)
    ATTRS_TO_EXPOSE = dataset_id
    COMBINE_GEOM = Use Result
    POSTGIS_PASSWORD = $(config_pass)
    ATTR_CONFLICT_RES = Use Result
    <OTHER> -> AttributeRenamer
AttributeRenamer
    ATTR_TABLE = RENAME_SET_DEFAULT id > geometry_id
    -> Reprojector_2
Reprojector_2
    SOURCE = EPSG:4326
    DEST = EPSG:25833
    RASTER_CELL_SIZE = Preserve Cells
    INTERPOLATION_TYPE_NAME = Nearest Neighbor
    REPROJECTED -> FeatureMerger_2 [REQUESTOR]
    REPROJECTED -> FeatureMerger [REQUESTOR]

Bookmark: AR-geometry
FeatureMerger_2
    ATTR_ACCUM_MODE = Merge Supplier
    REJECT_NULL_MISSING_KEYS = Yes
    JOIN_KEYS = @Value(dataset_id) @Value(dataset_id) AUTO
    PROCESS_DUPS = No
    IGNORE_NULLS = No
    ATTR_CONFLICT_RES = Use Requestor
    SUPPLIERS_FIRST = No
    MERGE_TYPE = Attributes Only
    MERGED -> GeometryFilter
GeometryFilter
    GEOM_PORT_NAMES = Point Line Area Surface
    BREAK_AGG = No
    POINT -> AttributeRenamer_5
AttributeRenamer_5
    ATTR_TABLE = RENAME_SET_DEFAULT geometry_id > geometry_id_ar
    -> PointOnAreaOverlayer_2 [POINT]

Bookmark: All geometry sans AR
FeatureMerger
    ATTR_ACCUM_MODE = Merge Supplier
    REJECT_NULL_MISSING_KEYS = Yes
    JOIN_KEYS = @Value(dataset_id) @Value(dataset_id) AUTO
    PROCESS_DUPS = No
    IGNORE_NULLS = No
    ATTR_CONFLICT_RES = Use Requestor
    SUPPLIERS_FIRST = No
    MERGE_TYPE = Attributes Only
    MERGED -> PointOnAreaOverlayer_2 [AREA]
    MERGED -> AreaCalculator

Bookmark: Intersect geometry
PointOnAreaOverlayer_2
    ATTR_ACCUM_MODE = Merge Incoming
    CANDIDATE_LIST_ATTRS_TO_INCLUDE = geometry_id_ar
    DEAGGREGATE_INPUT = Yes
    POLYS_FIRST = NO
    OV_ATTR = _overlaps
    ATTR_CONFLICT_RES = Use Original
    CANDIDATE_LIST_NAME = _relationships
    CANDIDATE_LIST_ATTRS_TO_INCLUDE_MODE = Selected Attributes
    AREA -> Tester_2
    <REJECTED> -> PointOnAreaOverlayer_2__Rejected_
PointOnAreaOverlayer_2__Rejected_: Logger
    MAXFEATS = 20
    MESSAGE = Feature is:
    MAXCOORDS = 20
Tester_2
    TEST_DESCRIPTION = ""
    TEST_MODE = Automatic
    TEST_CLAUSE = TEST @Value(_overlaps) > 0
    BOOL_OP = OR
    PASSED -> GeometryRemover
GeometryRemover
    -> ListExploder_2

Bookmark: Join in AR-codes
ListExploder_2
    INDEX_ATTR = _element_index
    ATTR_ACCUM_MODE = Merge List Attributes
    LIST_ATTR = _relationships{}
    ATTR_CONFLICT_RES = Use List Attribute Values
    ELEMENTS -> DatabaseJoiner_2
DatabaseJoiner_2
    ATTR_ACCUM_MODE = Merge Joined
    PREFETCH_EXHAUSTIVE = Yes
    POSTGRES_HOST = $(config_host)
    ADDED_FIELDS = code
    MATCH_MULTIPLE_DISPLAY = Create a feature for each match
    CACHE_SIZE = 5000
    TABLE = data.codes_geometry
    JOIN_KEYS = geometry_id_ar geometry_id
    POSTGRES_QUERY_FEATURE_TYPES_FOR_MERGE_FILTERS = Yes
    DATASET = $(config_db)
    POSTGRES_PORT = 5432
    POSTGRES_PASSWORD = $(config_pass)
    FORMAT = POSTGRES
    POSTGRES_USER_NAME = $(config_user)
    MATCH_RULE_DISPLAY = Match All (1:M)
    ATTR_CONFLICT_RES = Use Original
    JOINED -> AttributeRenamer_4
AttributeRenamer_4
    ATTR_TABLE = RENAME_SET_DEFAULT code > code_ar
    -> DatabaseJoiner
    -> DatabaseJoiner_3 [off]

Bookmark: Only keep species or lower
DatabaseJoiner_3 [off]
    ATTR_ACCUM_MODE = Merge Joined
    PREFETCH_EXHAUSTIVE = Yes
    POSTGRES_HOST = $(config_host)
    ADDED_FIELDS = level
    MATCH_MULTIPLE_DISPLAY = Create a feature for each match
    CACHE_SIZE = 5000
    TABLE = data.codes
    JOIN_KEYS = code_ar code
    POSTGRES_QUERY_FEATURE_TYPES_FOR_MERGE_FILTERS = Yes
    DATASET = $(config_db)
    POSTGRES_PORT = 5432
    POSTGRES_PASSWORD = $(config_pass)
    FORMAT = POSTGRES
    POSTGRES_USER_NAME = $(config_user)
    MATCH_RULE_DISPLAY = Match All (1:M)
    ATTR_CONFLICT_RES = Use Original
    JOINED -> Tester [off]
Tester [off]
    TEST_DESCRIPTION = ""
    TEST_MODE = Automatic
    TEST_CLAUSE = TEST @Value(level) > 7
    BOOL_OP = OR
    PASSED -> DatabaseJoiner [off]

Bookmark: Join in other codes
DatabaseJoiner
    ATTR_ACCUM_MODE = Merge Joined
    PREFETCH_EXHAUSTIVE = Yes
    POSTGRES_HOST = $(config_host)
    ADDED_FIELDS = code
    MATCH_MULTIPLE_DISPLAY = Create a feature for each match
    CACHE_SIZE = 5000
    TABLE = data.codes_geometry
    JOIN_KEYS = geometry_id geometry_id
    POSTGRES_QUERY_FEATURE_TYPES_FOR_MERGE_FILTERS = Yes
    DATASET = $(config_db)
    POSTGRES_PORT = 5432
    POSTGRES_PASSWORD = $(config_pass)
    FORMAT = POSTGRES
    POSTGRES_USER_NAME = $(config_user)
    MATCH_RULE_DISPLAY = Match All (1:M)
    ATTR_CONFLICT_RES = Use Original
    JOINED -> AttributeKeeper
AttributeKeeper
    KEEP_ATTRS = code_ar,code,geometry_id
    -> Aggregator_2

Bookmark: Join in predecessor
Aggregator_2
    ACCUM_ATTRS_NAME = Merge Incoming Attributes
    GROUP_BY = code
    MODE = Attributes Only
    ORDERED = No
    SEP = ,
    CONCAT_ATTRS = code_ar geometry_id
    AGGREGATE -> FeatureMerger_4 [REQUESTOR]
    AGGREGATE -> DatabaseJoiner_5
DatabaseJoiner_5
    ATTR_ACCUM_MODE = Merge Joined
    PREFETCH_EXHAUSTIVE = Yes
    POSTGRES_HOST = $(config_host)
    ADDED_FIELDS = predecessor
    MATCH_MULTIPLE_DISPLAY = Create a feature for each match
    CACHE_SIZE = 5000
    TABLE = data.codeshierarchy
    JOIN_KEYS = code successor
    POSTGRES_QUERY_FEATURE_TYPES_FOR_MERGE_FILTERS = Yes
    DATASET = $(config_db)
    POSTGRES_PORT = 5432
    POSTGRES_PASSWORD = $(config_pass)
    FORMAT = POSTGRES
    POSTGRES_USER_NAME = $(config_user)
    MATCH_RULE_DISPLAY = Match All (1:M)
    ATTR_CONFLICT_RES = Use Original
    JOINED -> Aggregator_5
Aggregator_5
    ACCUM_ATTRS_NAME = Merge Incoming Attributes
    GROUP_BY = predecessor
    MODE = Attributes Only
    ORDERED = No
    SEP = ,
    CONCAT_ATTRS = code_ar code geometry_id
    AGGREGATE -> PythonCaller
    AGGREGATE -> FeatureMerger_4 [SUPPLIER]

Bookmark: Add in codes that aren't predecessors
FeatureMerger_4
    ATTR_ACCUM_MODE = Merge Supplier
    REJECT_NULL_MISSING_KEYS = No
    JOIN_KEYS = @Value(code) @Value(predecessor) AUTO
    PROCESS_DUPS = Yes
    CONNECT_Z_MODE = First Wins
    IGNORE_NULLS = No
    GEOM_TYPE = Build Polygons
    ATTR_CONFLICT_RES = Use Requestor
    SUPPLIERS_FIRST = No
    MERGE_TYPE = Attributes Only
    UNMERGED_REQUESTOR -> AttributeCreator_2
AttributeCreator_2
    ATTR_TABLE = SET_TO predecessor = @Value(code)
    -> PythonCaller

Bookmark: Count unique values
PythonCaller
    NEW_ATTRIBUTES = _count_code_ar _count_geometry_id
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def findUnique(_self, feature, attribute):
              naDict = {}
              for na in feature.getAttribute(attribute).split(','):
                  naDict[na] = True
              naString = ""
              for na in naDict.keys():
                  naString += na + ','
              feature.setAttribute(attribute, naString[:-1])
              feature.setAttribute('_count_' + attribute, len(naDict.keys()))

          def input(self,feature):
              self.findUnique(feature, 'code_ar')
              self.findUnique(feature, 'geometry_id')

              self.pyoutput(feature)
          def close(self):
              pass
    PYTHONSYMBOL = FeatureProcessor
    -> AttributeSplitter
AttributeSplitter
    LIST_NAME = _list_geometry_id
    DROP_EMPTY_PARTS = No
    ATTR_NAME = geometry_id
    DELIMITER = ,
    TRIM_OPTION = Both
    -> ListExploder
ListExploder
    INDEX_ATTR = _element_index
    ATTR_ACCUM_MODE = Merge List Attributes
    LIST_ATTR = _list_geometry_id{}
    ATTR_CONFLICT_RES = Use List Attribute Values
    ELEMENTS -> FeatureMerger_3 [REQUESTOR]

Bookmark: Calculate area
AreaCalculator
    MULT = 1
    AREA_TYPE = Plane Area
    AREA_ATTR = _area
    -> GeometryRemover_2
    <REJECTED> -> AreaCalculator__Rejected_
AreaCalculator__Rejected_: Logger
    MAXFEATS = 20
    MESSAGE = Feature is:
    MAXCOORDS = 20
GeometryRemover_2
    -> FeatureMerger_3 [SUPPLIER]

Bookmark: Sum area on predecessor
FeatureMerger_3
    ATTR_ACCUM_MODE = Merge Supplier
    REJECT_NULL_MISSING_KEYS = No
    JOIN_KEYS = @Value(_list_geometry_id) @Value(geometry_id) AUTO
    PROCESS_DUPS = Yes
    CONNECT_Z_MODE = First Wins
    IGNORE_NULLS = No
    GEOM_TYPE = Build Polygons
    ATTR_CONFLICT_RES = Use Requestor
    SUPPLIERS_FIRST = No
    MERGE_TYPE = Attributes Only
    MERGED -> Aggregator
Aggregator
    ACCUM_ATTRS_NAME = Use Attributes From One Feature
    GROUP_BY = predecessor
    SUM = _area
    MODE = Attributes Only
    ORDERED = No
    SEP = ,
    AGGREGATE -> JSONTemplater_4 [ROOT]

Bookmark: Write to json
JSONTemplater_4
    RESULT_ATTRIBUTE = _result
    ROOT_QUERY_EXPR:
      {
          fme:get-attribute("predecessor"): {
              "area": @int64(@Value("_area")),
              "observedSpecies": fme:get-attribute("_count_code_ar"),
              "areas": fme:get-attribute("_count_geometry_id")
              }
      }
    VISIBLE_QUERY_VALIDATE = Yes
    -> ListBuilder_2
ListBuilder_2
    LIST_NAME = _list
    LIST_ATTRS_TO_INCLUDE = _result
    GROUPS_ORDERED = No
    -> JSONTemplater_2 [ROOT]
JSONTemplater_2
    RESULT_ATTRIBUTE = _result
    ROOT_QUERY_EXPR = [ fme:get-json-list-attribute("_list{}._result") ]
    VISIBLE_QUERY_VALIDATE = Yes
    -> text_line (writer TEXTLINE_1)
text_line (writer TEXTLINE_1)
    attributes: text_line_data buffer
