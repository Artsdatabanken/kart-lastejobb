FME workspace 03_titles.fmw

Parameters:
- DestDataset_TEXTLINE = D:\out\json\codes\titles.json   # Destination Text File
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_port:   # Python Script
      import fme
      import json
      
      data = json.load(open('../../config/postgis.json'))
      
      return data['port']
- config_host:   # Python Script
      import fme
      import json
      
      data = json.load(open('../../config/postgis.json'))
      
      return data['host']

Writers:
- TEXTLINE_1: TEXTLINE to $(DestDataset_TEXTLINE)

Creator
    GEOMTYPE = Geometry Object
    NUM = 1
    CREATED -> SQLExecutor_2 [INITIATOR]
SQLExecutor_2
    POSTGRES_USER_NAME = $(config_user)
    COMBINE_GEOM = Initiator Geometry Only
    POSTGRES_PASSWORD = $(config_pass)
    DATASET = $(config_db)
    POSTGRES_QUERY_FEATURE_TYPES_FOR_MERGE_FILTERS = Yes
    POSTGRES_HOST = $(config_host)
    COMBINE_ATTRS = Keep Result Attributes if Conflict
    SQL_STATEMENT:
      select c.code, c.title
      from
      data.codes c
    EXPOSED_ATTRIBUTE_LIST = code,title
    FORMAT = POSTGRES
    POSTGRES_PORT = $(config_port)
    RESULT -> PythonCaller_2
Note: Find codes that need an explanation
PythonCaller_2
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              code = feature.getAttribute('code')
              if(len(code.split("_")) < 3):
                  feature.setAttribute('parentCode', None)
                  self.pyoutput(feature)
              else:
                  parentCode = code.split("_")[0] + '_' + code.split("_")[1]
                  feature.setAttribute('parentCode', parentCode)
                  self.pyoutput(feature)
          def close(self):
              pass
    PYTHONSYMBOL = FeatureProcessor
    NEW_ATTRIBUTES = parentCode
    -> AttributeFilter
AttributeFilter
    ATTR_VALUES = <Empty>,<Missing>,<Null>,<Unfiltered>
    ATTR_NAME = parentCode
    <EMPTY> -> StringConcatenator_2
    <UNFILTERED> -> SQLExecutor_3 [INITIATOR]
StringConcatenator_2
    ACTION = Create New Attribute
    VAL_ATTR = titles
    PARM_LINE = "@Value(code)" : { "title": "@Value(title)" } ,
    -> Aggregator
SQLExecutor_3
    POSTGRES_USER_NAME = $(config_user)
    COMBINE_GEOM = Initiator Geometry Only
    POSTGRES_PASSWORD = $(config_pass)
    DATASET = $(config_db)
    POSTGRES_QUERY_FEATURE_TYPES_FOR_MERGE_FILTERS = Yes
    POSTGRES_HOST = $(config_host)
    COMBINE_ATTRS = Keep Result Attributes if Conflict
    SQL_STATEMENT:
      select
      c.title as parent
      from
      data.codes c
      where
      c.code = '@Value(parentCode)'
    EXPOSED_ATTRIBUTE_LIST = parent
    FORMAT = POSTGRES
    POSTGRES_PORT = $(config_port)
    RESULT -> StringConcatenator_3
StringConcatenator_3
    ACTION = Create New Attribute
    VAL_ATTR = titles
    PARM_LINE = "@Value(code)" : { "title": "@Value(title)", "parent": "@Value(parent)" } ,
    -> Aggregator
Aggregator
    CONCAT_ATTRS = titles
    ORDERED = No
    MODE = Attributes Only
    ACCUM_ATTRS_NAME = Drop Incoming Attributes
    AGGREGATE -> text_line (writer TEXTLINE_1)
text_line (writer TEXTLINE_1)
    attributes: text_line_data buffer
