FME workspace 01_sqrt42.fmw

Parameters:
- mergeNeighbours = true   # true/false
- datasetId = 4   # DatasetId
- prefix = AO
- Resolution = 250
- DestDataset_GEOJSON = D:\out   # Destination GeoJSON File
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_port:   # Python Script
      import fme
      import json
      
      data = json.load(open('../../config/postgis.json'))
      
      return data['port']
- config_host:   # Python Script
      import fme
      import json
      
      data = json.load(open('../../config/postgis.json'))
      
      return data['host']

Writers:
- GEOJSON_1: GEOJSON to $(DestDataset_GEOJSON)

FeatureWriter_2_Summary: Logger
    LOG_FEATURE = LOG_ONLY
    MAXCOORDS = 20
    MAXFEATS = 20
    MESSAGE = Feature is:
    SEVERITY = INFO
NumericRasterizer_3__Rejected_: Logger
    LOG_FEATURE = LOG_ONLY
    MAXCOORDS = 20
    MAXFEATS = 20
    MESSAGE = Feature is:
    SEVERITY = INFO
FeatureWriter_Summary: Logger
    LOG_FEATURE = LOG_ONLY
    MAXCOORDS = 20
    MAXFEATS = 20
    MESSAGE = Feature is:
    SEVERITY = INFO
GeometryValidator_Failed: Logger
    LOG_FEATURE = LOG_ONLY
    MAXCOORDS = 20
    MAXFEATS = 20
    MESSAGE:
      Feature is:
      Geometry_id: @Value(geometry_id),
      Code: @Value(code),
      Issue: @Value(_issues{0}.issue_found)
    SEVERITY = WARN

Bookmark: Merge codes and geometry
Creator
    GEOMTYPE = Geometry Object
    NUM = 1
    CREATED -> FeatureReader [INITIATOR]
    CREATED -> FeatureReader_4 [INITIATOR]
FeatureReader_4
    ATTRS_TO_EXPOSE = geometry_id code
    ATTR_ACCUM_MODE = Merge Initiator and Result
    ATTR_CONFLICT_RES = Use Result
    COMBINE_GEOM = Use Result
    DATASET = $(config_db)
    FEATURETYPES = data.codes_geometry
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_HOST = $(config_host)
    POSTGIS_PASSWORD = $(config_pass)
    POSTGIS_PORT = $(config_port)
    POSTGIS_POSTGIS_EXPOSE_FORMAT_ATTRS = postgres_oid,int4
    POSTGIS_QUERY_FEATURE_TYPES_FOR_MERGE_FILTERS = Yes
    POSTGIS_USER_NAME = $(config_user)
    POSTGIS_USE_SEARCH_ENVELOPE = NO
    POSTGIS_USE_TRUE_POSTGIS_TYPES = yes
    <OTHER> -> DuplicateFilter_2
DuplicateFilter_2
    INPUT_ORDERED_CHOICE = No
    KEYATTR = code geometry_id
    UNIQUE -> FeatureMerger [REQUESTOR]
FeatureReader
    ATTRS_TO_EXPOSE = id
    ATTR_ACCUM_MODE = Merge Initiator and Result
    ATTR_CONFLICT_RES = Use Result
    COMBINE_GEOM = Use Result
    DATASET = $(config_db)
    FEATURETYPES = data.geometry
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_HOST = $(config_host)
    POSTGIS_PASSWORD = $(config_pass)
    POSTGIS_PORT = $(config_port)
    POSTGIS_POSTGIS_EXPOSE_FORMAT_ATTRS = postgres_oid,int4
    POSTGIS_QUERY_FEATURE_TYPES_FOR_MERGE_FILTERS = Yes
    POSTGIS_USER_NAME = $(config_user)
    POSTGIS_USE_SEARCH_ENVELOPE = NO
    POSTGIS_USE_TRUE_POSTGIS_TYPES = yes
    <OTHER> -> FeatureMerger [SUPPLIER]
FeatureMerger
    ATTR_ACCUM_MODE = Merge Supplier
    ATTR_CONFLICT_RES = Use Requestor
    IGNORE_NULLS = No
    JOIN_KEYS = @Value(geometry_id) @Value(id) AUTO
    MERGE_TYPE = Attributes and Geometry
    PROCESS_DUPS = NO
    REJECT_NULL_MISSING_KEYS = No
    SUPPLIERS_FIRST = No
    MERGED -> DatabaseJoiner

Bookmark: Get data about code and merge in leafnodes
DatabaseJoiner
    ADDED_FIELDS = title predecessor index
    ATTR_ACCUM_MODE = Merge Joined
    ATTR_CONFLICT_RES = Use Joined
    CACHE_SIZE = 200000
    DATASET = $(config_db)
    FORMAT = POSTGRES
    JOIN_KEYS = code code
    MATCH_MULTIPLE_DISPLAY = Create a feature for each match
    MATCH_RULE_DISPLAY = Match All (1:M)
    POSTGRES_HOST = $(config_host)
    POSTGRES_PASSWORD = $(config_pass)
    POSTGRES_PORT = 5432
    POSTGRES_QUERY_FEATURE_TYPES_FOR_MERGE_FILTERS = Yes
    POSTGRES_READ_TIME_WITH_TIMEZONE = Yes
    POSTGRES_USER_NAME = $(config_user)
    PREFETCH_EXHAUSTIVE = Yes
    PREFETCH_QUERY = select code, title, predecessor, index from data.codes
    TABLE = data.codes
    JOINED -> AttributeRenamer
    JOINED -> FeatureMerger_2 [SUPPLIER]
Note: Select leafnodes
SQLCreator
    DATASET = $(config_db)
    EXPOSED_ATTRIBUTE_LIST = code,title,predecessor,index
    FORMAT = POSTGRES
    POSTGRES_HOST = $(config_host)
    POSTGRES_PASSWORD = $(config_pass)
    POSTGRES_PORT = 5432
    POSTGRES_QUERY_FEATURE_TYPES_FOR_MERGE_FILTERS = Yes
    POSTGRES_READ_TIME_WITH_TIMEZONE = Yes
    POSTGRES_USER_NAME = $(config_user)
    SQL_STATEMENT:
      select
      distinct c.code, title, c.code as predecessor, index
      from
      data.codes c,
      data.codes_geometry cg
      where
      cg.codes_id = c.id
      and NOT EXISTS (select 1 from data.codes c2, data.codes_geometry cg2 where c2.predecessor = c.code and cg2.codes_id = c2.id)


      --select code, title, code as predecessor, index
      --from data.codes c1
      --where NOT EXISTS (select 1 from data.codes c2, data.codes_geometry cg where c2.predecessor = c1.code and cg.codes_id = c2.id)
    RESULT -> FeatureMerger_2 [REQUESTOR]
Note: Add leafnodes
FeatureMerger_2
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(code) @Value(code) AUTO
    MERGE_TYPE = Attributes and Geometry
    PROCESS_DUPS = YES
    REJECT_NULL_MISSING_KEYS = No
    SUPPLIERS_FIRST = No
    MERGED -> AttributeRenamer
AttributeRenamer
    ATTR_TABLE:
      RENAME_SET_DEFAULT title > name
      RENAME_SET_DEFAULT predecessor > filename
    -> AttributeFilter
AttributeFilter
    ATTR_NAME = name
    ATTR_VALUES = <Empty>,<Missing>,<Null>,<Unfiltered>
    <EMPTY> -> AttributeCreator_5
    <MISSING> -> AttributeCreator_5
    <NULL> -> AttributeCreator_5
    <UNFILTERED> -> Deaggregator_2
AttributeCreator_5
    ATTR_TABLE = SET_TO name = @Value(code)
    -> Deaggregator_2

Bookmark: Switch
Deaggregator_2
    EXPLODE_INSTANCES = Yes
    GEOM_NAME_FIELD = _geometry_name
    LIST_ATTR_MODE_LOOKUP = LEAN
    MODE = Flatten All Levels
    SPLIT_COMPOSITES = No
    DEAGGREGATED -> GeometryValidator
GeometryValidator
    ANGULAR_TOLERANCE_CHOICE = Automatic
    ARC_ENDPOINT_TOLERANCE_MODE = Auto
    AREA_ORIENTATION = AREA_ORIENTATION
    CHECK_AREA_CHOICE = No
    CHECK_HOLE_TOUCHING_POLYGON = No
    CONNECT_Z_MODE_SI = First Wins
    CONNECT_Z_MODE_TR = First Wins
    CONSECUTIVE_IDENTICAL_VERTICES_2D = CONSECUTIVE_IDENTICAL_VERTICES_2D
    DUP_COORDS_CHECK_Z = No
    ISSUE_ATTR_NAME = _issues
    MISSING_TEXTURE_COORDINATES = MISSING_TEXTURE_COORDINATES
    MISSING_VERTEX_NORMALS = MISSING_VERTEX_NORMALS
    NAN_REMOVAL = NAN_REMOVAL
    NULL_REMOVAL = NULL_REMOVAL
    ORIENTATION_CHECK_DIR = Valid
    PLANAR_SURFACE = PLANAR_SURFACE
    PRESETS = Custom
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    SELF_INTERSECTING = SELF_INTERSECTING
    SUMMARY = Detailed
    THICKNESS_TOLERANCE_CHOICE = Automatic
    TYPE_REPAIR = TYPE_REPAIR
    PASSED -> AttributeKeeper
    FAILED -> GeometryValidator_Failed
    REPAIRED -> AttributeKeeper
AttributeKeeper
    KEEP_ATTRS = filename,name,index,code
    -> GeometryFilter
    -> JSONTemplater_2 [ROOT]
GeometryFilter
    BREAK_AGG = No
    GEOM_PORT_NAMES = Area
    AREA -> AreaGapAndOverlapCleaner
    <UNFILTERED> -> Reprojector
    <UNFILTERED> -> Reprojector_3

Bookmark: Write json for code/index-mapping
JSONTemplater_2 [off]
    CONSECUTIVE_GROUPS = No
    GROUP_BY = filename
    RESULT_ATTRIBUTE = _result
    ROOT_QUERY_EXPR:
      {
          fme:get-attribute("code"): fme:get-attribute("index")
      }
    VISIBLE_QUERY_VALIDATE = Yes
    -> ListBuilder
    -> DuplicateFilter
ListBuilder
    GROUPS_ORDERED = No
    GROUP_BY = filename
    LIST_ATTRS_TO_INCLUDE = _result
    LIST_NAME = _list
    -> JSONTemplater [ROOT]
DuplicateFilter
    INPUT_ORDERED_CHOICE = No
    KEYATTR = code index
    UNIQUE -> JSONTemplater [CODE]
JSONTemplater
    CODE_QUERY_EXPR = {fme:get-json-attribute("_result")}
    CONSECUTIVE_GROUPS = No
    GROUP_BY = filename
    RESULT_ATTRIBUTE = _result
    ROOT_QUERY_EXPR = {[fme:process-features("CODE")]}
    VISIBLE_QUERY_VALIDATE = Yes
    -> Tester_3
Tester_3
    BOOL_OP = OR
    TEST_CLAUSE = "TEST @Value(_result) NOT_= {  }\n"
    PASSED -> AttributeCreator_7
AttributeCreator_7
    ATTR_TABLE = SET_TO folder = @ReplaceString(@Value(filename),-,\)\
    -> FeatureWriter_2 [text_line]
FeatureWriter_2
    DATASET = d:\out\@Value(folder)\raster.3857.24bit.png.metadata.json
    DATASET_ATTR = _dataset
    FEATURE_TYPE_LIST_ATTR = _feature_type
    FORMAT = TEXTLINE
    TEXTLINE_COORDINATE_SYSTEM_GRANULARITY = FEATURE
    TEXTLINE_DESTINATION_DATASETTYPE_VALIDATION = Yes
    TEXTLINE_ENCODING = SYSTEM
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    SUMMARY -> FeatureWriter_2_Summary

Bookmark: Clean Areas
AreaGapAndOverlapCleaner
    CLEANING_TOLERANCE = Automatic
    CONNECT_Z_MODE = First Wins
    DEAGGREGATE_INPUT = YES
    FILL_ALL_GAPS = No
    GROUP_BY = filename code
    MEASURE_TYPE = Continuous
    MISSING_VAL_MODE = Compute
    REPAIR_METHOD = Longest Boundary
    REPAIRED -> Deaggregator
Deaggregator
    EXPLODE_INSTANCES = Yes
    GEOM_NAME_FIELD = _geometry_name
    LIST_ATTR_MODE_LOOKUP = LEAN
    MODE = Flatten All Levels
    SPLIT_COMPOSITES = No
    DEAGGREGATED -> Sorter
Sorter
    SORT_PARM = filename ALPHA ASCENDING code ALPHA ASCENDING
    SORTED -> Dissolver
Dissolver
    ACCUM_INPUT_ATTRS = Use Attributes From One Feature
    CONNECT_Z_MODE = Ignore
    DEAGGREGATE_INPUT = Yes
    GROUP_BY = code filename
    NO_OVRLP = Yes
    AREA -> Reprojector
    AREA -> Reprojector_3

Bookmark: Write Raster
Reprojector_3 [off]
    DEST = EPSG:3857
    INTERPOLATION_TYPE_NAME = Nearest Neighbor
    RASTER_CELL_SIZE = Preserve Cells
    RASTER_TOLERANCE = 0.0
    SOURCE = EPSG:4326
    REPROJECTED -> 3DForcer
3DForcer
    KEEPZVAL = No
    ZVALATTR = @Value(index)
    -> Aggregator_2
Aggregator_2
    ACCUM_ATTRS_NAME = Use Attributes From One Feature
    AGGREGATE_TYPE = Homogeneous Collection (If Possible)
    GROUP_BY = filename
    MODE = Geometry - Assemble One Level
    ORDERED = No
    SEP = ,
    AGGREGATE -> BoundsExtractor
BoundsExtractor
    XMAX = _xmax
    XMIN = _xmin
    YMAX = _ymax
    YMIN = _ymin
    ZMAX = _zmax
    ZMIN = _zmin
    -> NumericRasterizer_3
NumericRasterizer_3
    ANTI_ALIASING = No
    BACKGROUND_VALUE = 0
    FILL_WITH_NODATA = Yes
    GROUND_EXTENTS_MAX_X = (@int((@Value(_xmax)/$(Resolution))) * $(Resolution)) + $(Resolution)
    GROUND_EXTENTS_MAX_Y = (@int((@Value(_ymax)/$(Resolution))) * $(Resolution)) +$(Resolution)
    GROUND_EXTENTS_MIN_X = (@int((@Value(_xmin)/$(Resolution))) * $(Resolution) )- $(Resolution)
    GROUND_EXTENTS_MIN_Y = (@int((@Value(_ymin)/$(Resolution))) * $(Resolution)) - $(Resolution)
    GROUP_BY = code filename
    INTERPRETATION_TYPE = UInt32
    ROWCOL_OR_CELLSIZE = CellSize
    SPECIFY_GROUND_EXTENTS = Specify ground extents
    TOLERANCE = 0.5
    X_CELL_SIZE = 250
    Y_CELL_SIZE = 250
    RASTER -> RasterExpressionEvaluator_2 [A]
    <REJECTED> -> NumericRasterizer_3__Rejected_
Note: Make RGB-representation of index
RasterExpressionEvaluator_2
    EXPRESSION_LIST = INTERPRETATION_LIST "RED8;GREEN8;BLUE8" EXPRESSION_LIST "A[0]  >> 16;( (A[0]  >> 8) -( (A[0] >>16) << 8 ) );A[0] - (( A[0]  >> 8) << 8 )"
    MODE = One Raster
    RESULT -> AttributeCreator_6
AttributeCreator_6
    ATTR_TABLE = SET_TO folder = @ReplaceString(@Value(filename),-,\)\
    -> FeatureWriter [Raster1]
FeatureWriter
    COORDSYS = EPSG:3857
    DATASET = D:\out\@Value(folder)
    DATASET_ATTR = _dataset
    FEATURE_TYPE_LIST_ATTR = _feature_type
    FORMAT = PNGRASTER
    TOTAL_FEATURES_WRITTEN_ATTR = _total_features_written
    SUMMARY -> FeatureWriter_Summary

Bookmark: Calculate area
Reprojector
    DEST = EPSG:25833
    INTERPOLATION_TYPE_NAME = Nearest Neighbor
    RASTER_CELL_SIZE = Preserve Cells
    RASTER_TOLERANCE = 0.0
    SOURCE = EPSG:4326
    REPROJECTED -> AreaCalculator
AreaCalculator
    AREA_ATTR = area
    AREA_TYPE = Plane Area
    MULT = 1
    -> AttributeRounder
    <REJECTED> -> AttributeRounder
AttributeRounder
    PLACES = 0
    ROUND_TYPE = Nearest
    SRC_ATTRS = area
    -> Reprojector_2
Reprojector_2
    DEST = EPSG:4326
    INTERPOLATION_TYPE_NAME = Nearest Neighbor
    RASTER_CELL_SIZE = Preserve Cells
    RASTER_TOLERANCE = 0.0
    SOURCE = EPSG:25833
    REPROJECTED -> AttributeCreator_3

Bookmark: Write GeoJson
AttributeCreator_3
    ATTR_TABLE = SET_TO folder = @ReplaceString(@Value(filename),-,\)\vector.4326.geojson
    -> NewFeatureType (writer GEOJSON_1)
NewFeatureType (writer GEOJSON_1)
    attributes: name string, code string, index string, _geometry_name string, area string
