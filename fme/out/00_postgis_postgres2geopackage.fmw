FME workspace 00_postgis_postgres2geopackage.fmw

Parameters:
- SourceDataset_POSTGIS = bigbadabom   # Connection
- SourceDataset_POSTGRES = bigbadabom   # Connection
- DestDataset_GEOPACKAGE = D:\out\db\bigbadabom.gpkg   # GeoPackage File
- DestDataset_SPATIALITE = D:\out\db\bigbadabom.sqlite   # SpatiaLite Database

Readers:
- POSTGIS_1: POSTGIS from $(SourceDataset_POSTGIS)
- POSTGRES_1: POSTGRES from $(SourceDataset_POSTGRES)

Writers:
- GEOPACKAGE_1: GEOPACKAGE to $(DestDataset_GEOPACKAGE)
- SPATIALITE_1: SPATIALITE to $(DestDataset_SPATIALITE)

Bookmark: PostGIS
prefix (reader POSTGRES_1)
    attributes: id serial,PrimaryKey, value text,PrimaryKey, description text
    -> data_prefix (writer GEOPACKAGE_1)
    -> data_prefix (writer SPATIALITE_1)
localid_geometry (reader POSTGRES_1)
    attributes: geometry_id int8,BTree, localid text,BTree
    -> data_localid_geometry (writer GEOPACKAGE_1)
    -> data_localid_geometry (writer SPATIALITE_1)
dataset (reader POSTGRES_1)
    attributes: id int8,PrimaryKey, prefix_id int4,BTree, description text
    -> data_dataset (writer GEOPACKAGE_1)
    -> data_dataset (writer SPATIALITE_1)
codeshierarchy (reader POSTGRES_1)
    attributes: id int8,PrimaryKey, predecessor text,BTree, successor text,BTree
    -> data_codeshierarchy (writer GEOPACKAGE_1)
    -> data_codeshierarchy (writer SPATIALITE_1)
codes_geometry (reader POSTGRES_1)
    attributes: geometry_id int8,PrimaryKey, code text, codes_id int8, fraction int4, created timestamp
    -> data_codes_geometry (writer GEOPACKAGE_1)
    -> data_codes_geometry (writer SPATIALITE_1)
codes (reader POSTGRES_1)
    attributes: id int8,PrimaryKey, code text,PrimaryKey, title text, level int4, index int8
    -> data_codes (writer GEOPACKAGE_1)
    -> data_codes (writer SPATIALITE_1)
geometry (reader POSTGIS_1)
    attributes: id int8,PrimaryKey, geometry, dataset_id int4,BTree
    -> data_geometry (writer GEOPACKAGE_1)
    -> data_geometry (writer SPATIALITE_1)

Bookmark: Spatialite
data_prefix (writer SPATIALITE_1)
    attributes: id integer, value string(255), description string(255)
data_localid_geometry (writer SPATIALITE_1)
    attributes: geometry_id integer64, localid string(255)
data_dataset (writer SPATIALITE_1)
    attributes: id integer64, prefix_id integer, description string(255)
data_codeshierarchy (writer SPATIALITE_1)
    attributes: id integer64, predecessor string(255), successor string(255)
data_codes_geometry (writer SPATIALITE_1)
    attributes: geometry_id integer64, code string(255), codes_id integer64, fraction integer, created datetime
data_codes (writer SPATIALITE_1)
    attributes: id integer64, code string(255), title string(255), level integer, index integer64
data_geometry (writer SPATIALITE_1)
    attributes: id integer64, geometry, dataset_id integer

Bookmark: Geopackage
data_prefix (writer GEOPACKAGE_1)
    attributes: id mediumint, value text, description text
data_localid_geometry (writer GEOPACKAGE_1)
    attributes: geometry_id int, localid text
data_dataset (writer GEOPACKAGE_1)
    attributes: id int, prefix_id mediumint, description text
data_codeshierarchy (writer GEOPACKAGE_1)
    attributes: id int, predecessor text, successor text
data_codes_geometry (writer GEOPACKAGE_1)
    attributes: geometry_id int, code text, codes_id int, fraction mediumint, created datetime
data_codes (writer GEOPACKAGE_1)
    attributes: id int, code text, title text, level mediumint, index int
data_geometry (writer GEOPACKAGE_1)
    attributes: id int, geometry, dataset_id mediumint
