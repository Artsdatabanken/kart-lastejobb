FME workspace 02_bbox.fmw

Parameters:
- DestDataset_GEOJSON = D:\out\geojson\sqrt42\sqrt42.bbox.geojson   # Destination GeoJSON File
- DestDataset_TEXTLINE = D:\out\json\sqrt42\sqrt42bbox.json   # Destination Text File
- SourceDataset_MBTILES = D:\out\mbtiles\*-RASTER.mbtiles   # Source MBTiles File(s)
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_port:   # Python Script
      import fme
      import json
      
      data = json.load(open('../../config/postgis.json'))
      
      return data['port']
- config_host:   # Python Script
      import fme
      import json
      
      data = json.load(open('../../config/postgis.json'))
      
      return data['host']

Readers:
- MBTILES_1: MBTILES from $(SourceDataset_MBTILES)

Writers:
- GEOJSON_1: GEOJSON to $(DestDataset_GEOJSON)
- TEXTLINE_1: TEXTLINE to $(DestDataset_TEXTLINE)

Creator
    GEOMTYPE = Geometry Object
    NUM = 1
    CREATED -> FeatureReader [INITIATOR]
FeatureReader
    OUTPUT_FEATURES_DISPLAY = Schema and Data Features
    POSTGIS_USE_SEARCH_ENVELOPE = NO
    POSTGIS_QUERY_FEATURE_TYPES_FOR_MERGE_FILTERS = Yes
    DATASET = $(config_db)
    INTERACT = <No Spatial Filter>
    POSTGIS_FEATURES_PER_FETCH = 10000
    POSTGIS_USE_TRUE_POSTGIS_TYPES = yes
    ATTR_ACCUM_MODE = Only Use Result
    FEATURETYPES = data.geometry
    COMBINE_GEOM = Use Result
    POSTGIS_DISABLE_COLLECTION_SPLITTING = yes
    POSTGIS_HOST = $(config_host)
    POSTGIS_PORT = $(config_port)
    POSTGIS_USER_NAME = $(config_user)
    POSTGIS_PASSWORD = $(config_pass)
    FORMAT = POSTGIS
    <OTHER> -> SQLExecutor [INITIATOR]
Note: Join in all codes and predecessor-codes
SQLExecutor
    POSTGRES_USER_NAME = $(config_user)
    COMBINE_GEOM = Initiator Geometry Only
    POSTGRES_QUERY_FEATURE_TYPES_FOR_MERGE_FILTERS = Yes
    POSTGRES_PASSWORD = $(config_pass)
    FORMAT = POSTGRES
    POSTGRES_PORT = $(config_port)
    COMBINE_ATTRS = Keep Result Attributes if Conflict
    POSTGRES_HOST = $(config_host)
    SQL_STATEMENT:
      select u.codes as code
      from
      (
      select c.code as codes
      from
      data.codes c, data.codes_geometry cg
      where
      c.id = cg.codes_id
      and
      cg.geometry_id = @Value(id)
      union
      select ch.predecessor as codes
      from
      data.codes c, data.codes_geometry cg, data.codeshierarchy ch
      where
      c.id = cg.codes_id
      and
      cg.geometry_id = @Value(id)
      and
      ch.successor = c.code
      ) as u
    EXPOSED_ATTRIBUTE_LIST = code
    DATASET = $(config_db)
    RESULT -> AttributeFilter
AttributeFilter
    ATTR_VALUES = <Empty>,<Missing>,<Null>,<Unfiltered>
    ATTR_NAME = code
    <EMPTY> -> AttributeFilter__Empty_
    <MISSING> -> AttributeFilter__Empty_
    <NULL> -> AttributeFilter__Empty_
    <UNFILTERED> -> BoundingBoxAccumulator
AttributeFilter__Empty_: Logger
    MESSAGE = Feature is:
    MAXCOORDS = 20
    MAXFEATS = 20
BoundingBoxAccumulator
    TOPFER_INDEX = No
    ACCUM_ATTRS_NAME = Use Attributes From One Feature
    GROUP_BY = code
    BOUNDING_BOX -> CoordinateRounder
    BOUNDING_BOX -> sqrt42bbox (writer GEOJSON_1)
sqrt42bbox (writer GEOJSON_1) [off]
    attributes: code string
MBTILES (reader MBTILES_1)
    -> RasterExtentsCoercer
RasterExtentsCoercer
    EXTENTS_TYPE = Raster Extents
    EXTENTS -> AttributeCreator
AttributeCreator
    ATTR_TABLE = SET_TO code = @Value(fme_basename)
    -> Reprojector
Reprojector
    RASTER_CELL_SIZE = Preserve Cells
    DEST = EPSG:4326
    SOURCE = Read from feature
    INTERPOLATION_TYPE_NAME = Nearest Neighbor
    REPROJECTED -> CoordinateRounder
CoordinateRounder
    YPREC = 5
    XPREC = 5
    ZPREC = 5
    ROUNDED -> BoundsExtractor
BoundsExtractor
    XMIN = _xmin
    XMAX = _xmax
    ZMAX = _zmax
    YMIN = _ymin
    ZMIN = _zmin
    YMAX = _ymax
    -> StringConcatenator
StringConcatenator
    ACTION = Create New Attribute
    VAL_ATTR = _sw
    PARM_LINE = @Value(_xmin),@Value(_ymin)
    -> StringConcatenator_2
StringConcatenator_2
    ACTION = Create New Attribute
    VAL_ATTR = _ne
    PARM_LINE = @Value(_xmax),@Value(_ymax)
    -> AttributeKeeper_3
AttributeKeeper_3
    KEEP_ATTRS = _sw,code,_ne
    -> StringConcatenator_3
    -> HTTPCaller
StringConcatenator_3
    ACTION = Create New Attribute
    VAL_ATTR = bbox
    PARM_LINE = "@Value(code)" : [ @Value(_ne), @Value(_sw) ]
    -> ListBuilder
ListBuilder
    GROUPS_ORDERED = No
    LIST_ATTRS_TO_INCLUDE = bbox
    LIST_NAME = _list
    -> ListConcatenator
ListConcatenator
    LIST_ATTR = _list{}.bbox
    VAL_ATTR = bbox
    DROP_EMPTY_PARTS = No
    SEP = ,
    -> text_line (writer TEXTLINE_1)
text_line (writer TEXTLINE_1)
    attributes: text_line_data buffer
HTTPCaller [off]
    ERROR_ATTR = _error
    HTTP_METHOD = PUT
    STATUS_CODE_ATTR = _http_status_code
    UPLOAD_BODY = [ @Value(_ne), @Value(_sw) ]
    FOLLOW_REDIRECTS = Yes
    UPLOAD_CONTENT_TYPE = JSON (application/json)
    TARGET_URL = https://bboxcode.firebaseio.com/bbox2/@Value(code).json
    CONNECTION_TIMEOUT_LENGTH = 60
    SAVE_FILE = Attribute
    RESPONSE_HEADER_LIST_ATTR = _headers
    UPLOAD_TYPE = Specify Upload Body
    TARGET_ATTR = _response_body
    TARGET_ATTR_ENCODING = auto-detect
    VERIFY_SSL_CERTIFICATES = Yes
    TRANSFER_TIMEOUT_LENGTH = 90
    USE_COOKIES = No
