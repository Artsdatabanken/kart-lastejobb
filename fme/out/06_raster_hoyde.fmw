FME workspace 06_raster_hoyde.fmw

Parameters:
- DestDataset_MBTILES = D:\out\terrain   # Destination MBTiles Folder
- SourceDataset_USGS_DEM = D:\in\KV\DTM_50\Data\*.dem   # Source U.S. Geological Survey DEM File(s)
- SourceDataset_USGS_DEM_3 = D:\in\KV\DTM_50\Data\6803_50m_33.dem   # Source U.S. Geological Survey DEM File(s)
- NearestNeighbor = NearestNeighbor
- manualMinValue = 10
- offset = 100000

Readers:
- USGS_DEM_1: USGS_DEM from $(SourceDataset_USGS_DEM)
- USGS_DEM_2: USGS_DEM from $(SourceDataset_USGS_DEM_3)

Writers:
- MBTILES_1: MBTILES to $(DestDataset_MBTILES) in EPSG:3857

USGS_DEM (reader USGS_DEM_1)
    -> RasterBandNodataRemover
USGS_DEM (reader USGS_DEM_2) [off]
    -> RasterBandNodataRemover
RasterBandNodataRemover
    -> AttributeKeeper
AttributeKeeper
    -> RasterExpressionEvaluator_4 [A]
Note: Make NoData 0
RasterExpressionEvaluator_4
    EXPRESSION_LIST = INTERPRETATION_LIST "PRESERVE" EXPRESSION_LIST "if(A[0]==-32767,0,A[0])"
    MODE = One Raster
    RESULT -> RasterMosaicker
RasterMosaicker
    ACCUM_ATTRS_NAME = Use Attributes From One Feature
    INTERPOLATION_TYPE_NAME = Bilinear
    MERGE_PALETTES_NAME = Yes
    NODATA_OVERWRITE = No
    OVERLAPPING_VALUES = last
    SNAPPING_TYPE_NAME = Resample
    -> RasterAspectCalculator [off]
    -> RasterSlopeCalculator [off]
    -> TINGenerator [POINTS/LINES] [off]
    -> Reprojector_2
RasterAspectCalculator
    ALGORITHM = Horn
    INTERPOLATE_NODATA = No
    -> RasterExpressionEvaluator_6 [A]
Note: Convert to radians
RasterExpressionEvaluator_6
    EXPRESSION_LIST = INTERPRETATION_LIST "PRESERVE" EXPRESSION_LIST "A[0]*3.14/180"
    MODE = One Raster
    RESULT -> RasterExpressionEvaluator_5 [B]
RasterSlopeCalculator
    ALGORITHM = Horn
    INTERPOLATE_NODATA = No
    OUTPUT_TYPE = Degrees
    -> RasterExpressionEvaluator_7 [A]
Note: Convert to radians
RasterExpressionEvaluator_7
    EXPRESSION_LIST = INTERPRETATION_LIST "PRESERVE" EXPRESSION_LIST "A[0]*3.14/180"
    MODE = One Raster
    RESULT -> RasterExpressionEvaluator_5 [A]
RasterExpressionEvaluator_5
    EXPRESSION_LIST = INTERPRETATION_LIST "AUTO;AUTO;AUTO;AUTO;PRESERVE;PRESERVE" EXPRESSION_LIST "@cos(A[0]);@sin(A[0]);@cos(B[0]);@sin(B[0]);A[0];B[0]"
    MODE = Two Rasters
    RESULT -> RasterExpressionEvaluator_5_Result
RasterExpressionEvaluator_5_Result: Inspector
Note: Reprojector_2
Reprojector_2
    DEST = EPSG:3857
    INTERPOLATION_TYPE_NAME = Bilinear
    RASTER_CELL_SIZE = Preserve Cells
    RASTER_TOLERANCE = 0.0
    SOURCE = Read from feature
    REPROJECTED -> AttributeCreator [off]
    REPROJECTED -> AttributeCreator_2
Note: Mapbox
AttributeCreator
    ATTR_TABLE = SET_TO format = mapbox
    -> RasterSingularCellValueCalculator
Note: Convert to dm
RasterSingularCellValueCalculator
    OPERAND_ORDER = raster (operation) numeric value
    OPERATION = *
    PRESERVE_INTERPRETATION = Yes
    SCALAR = $(manualMinValue)
    -> RasterSingularCellValueCalculator_2
Note: Add offset
RasterSingularCellValueCalculator_2
    OPERAND_ORDER = raster (operation) numeric value
    OPERATION = +
    PRESERVE_INTERPRETATION = Yes
    SCALAR = $(offset)
    -> RasterExpressionEvaluator_2 [A]
RasterExpressionEvaluator_2
    EXPRESSION_LIST = INTERPRETATION_LIST "RED8;GREEN8;BLUE8" EXPRESSION_LIST "A[0]  >> 16;( (A[0]  >> 8) -( (A[0] >>16) << 8 ) );A[0] - (( A[0]  >> 8) << 8 )"
    MODE = One Raster
    RESULT -> AttributeCreator_3
Note: Mapzen
AttributeCreator_2
    ATTR_TABLE = SET_TO format = mapzen
    -> RasterSingularCellValueCalculator_3
Note: Add offset
RasterSingularCellValueCalculator_3
    OPERAND_ORDER = raster (operation) numeric value
    OPERATION = +
    PRESERVE_INTERPRETATION = Yes
    SCALAR = 32768
    -> RasterExpressionEvaluator_3 [A]
RasterExpressionEvaluator_3
    EXPRESSION_LIST = INTERPRETATION_LIST "RED8;GREEN8;BLUE8" EXPRESSION_LIST "@floor(A[0]/256);@floor(A[0]%256);@floor( (A[0] - @floor(A[0])) * 256 )"
    MODE = One Raster
    RESULT -> AttributeCreator_3
AttributeCreator_3
    ATTR_TABLE = SET_TO mbtile_name = terrarium
    -> Raster1 (writer MBTILES_1)
Raster1 (writer MBTILES_1)
Note: Hack to make normals wo math
TINGenerator
    TOLERANCE = 50
    TRIANGLES -> SurfaceNormalCalculator
SurfaceNormalCalculator
    Ok -> 3DForcer
    Ok -> 3DForcer_2
    Ok -> 3DForcer_3
3DForcer_3
    KEEPZVAL = No
    ZVALATTR = @Value(normalZ)*255
    -> NumericRasterizer_3
NumericRasterizer_3
    ANTI_ALIASING = No
    BACKGROUND_VALUE = 0
    COLUMNS = 50
    FILL_WITH_NODATA = Yes
    INTERPRETATION_TYPE = UInt8
    ROWCOL_OR_CELLSIZE = RowsColumns
    ROWS = 50
    SPECIFY_GROUND_EXTENTS = Use input data ground extents
    TOLERANCE = 0.5
    RASTER -> RasterExpressionEvaluator_10 [A]
RasterExpressionEvaluator_10
    EXPRESSION_LIST = INTERPRETATION_LIST "BLUE8" EXPRESSION_LIST "A[0]"
    MODE = One Raster
    RESULT -> RasterBandCombiner
3DForcer
    KEEPZVAL = No
    ZVALATTR = @Value(normalX)*255
    -> NumericRasterizer
NumericRasterizer
    ANTI_ALIASING = No
    BACKGROUND_VALUE = 0
    COLUMNS = 50
    FILL_WITH_NODATA = Yes
    INTERPRETATION_TYPE = UInt8
    ROWCOL_OR_CELLSIZE = RowsColumns
    ROWS = 50
    SPECIFY_GROUND_EXTENTS = Use input data ground extents
    TOLERANCE = 0.5
    RASTER -> RasterExpressionEvaluator_8 [A]
RasterExpressionEvaluator_8
    EXPRESSION_LIST = INTERPRETATION_LIST "RED8" EXPRESSION_LIST "A[0]"
    MODE = One Raster
    RESULT -> RasterBandCombiner
3DForcer_2
    KEEPZVAL = No
    ZVALATTR = @Value(normalY)*255
    -> NumericRasterizer_2
NumericRasterizer_2
    ANTI_ALIASING = No
    BACKGROUND_VALUE = 0
    COLUMNS = 50
    FILL_WITH_NODATA = Yes
    INTERPRETATION_TYPE = UInt8
    ROWCOL_OR_CELLSIZE = RowsColumns
    ROWS = 50
    SPECIFY_GROUND_EXTENTS = Use input data ground extents
    TOLERANCE = 0.5
    RASTER -> RasterExpressionEvaluator_9 [A]
RasterExpressionEvaluator_9
    EXPRESSION_LIST = INTERPRETATION_LIST "GREEN8" EXPRESSION_LIST "A[0]"
    MODE = One Raster
    RESULT -> RasterBandCombiner
RasterBandCombiner
    ACCUM_ATTRS = Use Attributes From One Feature
    -> NumericRasterizer_Raster
NumericRasterizer_Raster: Inspector

FME custom transformer SurfaceNormalCalculator
This custom transformer calculates the coefficients of unit normal vector for each introduced polygon (attributes "normalX", "normalY", "normalZ"). The angle (attribute Slope) to the vertical is also derived from the direction of the surface normal vector. Values of 0 indicate perpendicular, 90 horizontal polygons. Furthermore, the 2D area is output in the attribute "signedArea2D" per polygon. Depending on the sign, a statement can be made about the orientation of the polygon. Negative values indicate polygons clockwise, positive counter-clockwise direction-oriented.
In order to obtain meaningful results, it is important to ensure that only planar polygons are initiated. All non-area features are routed unchanged through the rejected port.

INPUT (input)
    -> GeometryFilter
Note: use only closed polygons
GeometryFilter
    BREAK_AGG = No
    POINT -> Invalid (output)
    LINE -> Invalid (output)
    ARC -> Invalid (output)
    AREA -> CoordinateCounter
    ELLIPSE -> Invalid (output)
    TEXT -> Invalid (output)
    RASTER -> Invalid (output)
    SURFACE -> Invalid (output)
    SOLID -> Invalid (output)
    COLLECTION -> Invalid (output)
    NULL -> Invalid (output)
CoordinateCounter
    CNT_ATTR = _coordcount
    -> PythonCaller
PythonCaller
    NEW_ATTRIBUTES = normalX normalY normalZ Slope signedArea2D
    PYTHONSOURCE:
      import math
      import fmeobjects
      # Template Function interface:
      def calcNormal(feature):

          counter0 = 0
          coordCount = feature.numVertices() - 1

          normalX = 0
          normalY = 0
          normalZ = 0
          areaTri = 0
          area = 0
          angle = 0

          # loop through the coordinates and calculate surface normal of the triangle formed by the
          # the point, its predecessor and its successor.
          while counter0 < coordCount:

              # get test coordinate and the ones before and after
              before = (counter0 + (coordCount - 1)) % coordCount
              after = (counter0 + (coordCount + 1)) % coordCount
              coords0 = feature.getCoordinate(before)
              coords1 = feature.getCoordinate(counter0)
              coords2 = feature.getCoordinate(after)

              # calculate normal
              x1 = coords0[0]
              x2 = coords1[0]
              x3 = coords2[0]

              y1 = coords0[1]
              y2 = coords1[1]
              y3 = coords2[1]

              z1 = coords0[2]
              z2 = coords1[2]
              z3 = coords2[2]

              normalX = normalX + ((y2-y1) * (z3-z1) - (y3-y1) * (z2-z1))
              normalY = normalY + ((z2-z1) * (x3-x1) - (z3-z1) * (x2-x1))
              normalZ = normalZ + ((x2-x1) * (y3-y1) - (x3-x1) * (y2-y1))

              counter0 = counter0 + 1

              # polygon area (Gauss area formula)
              areaTri = ((y2+y3)*(x2-x3))/2
              area = area + areaTri


          # normalize vector
          length = math.sqrt(normalX**2 + normalY**2 + normalZ**2)

          if length <> 0:
              normalX = normalX / length
              normalY = normalY / length
              normalZ = normalZ / length
          else:
              normalX = 0
              normalY = 0
              normalZ = 0

          # angle
          if normalZ <>0:
              angle = math.fabs(math.atan(math.sqrt(normalX**2+normalY**2)/normalZ)*(180/3.14))
          else:
              angle = 90


          # write normal to feature
          feature.setAttribute('normalX',normalX)
          feature.setAttribute('normalY',normalY)
          feature.setAttribute('normalZ',normalZ)
          feature.setAttribute('signedArea2D',area)
          feature.setAttribute('Slope',angle)
    PYTHONSYMBOL = calcNormal
    -> AttributeRemover_3
AttributeRemover_3
    REMOVE_ATTRS = _coordcount
    -> Ok (output)
Ok (output)
Invalid (output)
