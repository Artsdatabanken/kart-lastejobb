FME workspace 05_ninMetadata_projectsPrograms.fmw

Parameters:
- DestDataset_TEXTLINE_3 = D:\out\json\ninMetadata\prjPrg.json   # Destination Text File
- config_mssql_pass:   # Python Script
      import fme
      import json
      
      data = json.load(open('../../config/mssql.json'))
      
      return data['pass']
- config_mssql_user:   # Python Script
      import fme
      import json
      
      data = json.load(open('../../config/mssql.json'))
      
      return data['user']
- config_mssql_db:   # Python Script
      import fme
      import json
      
      data = json.load(open('../../config/mssql.json'))
      
      return data['db']
- config_mssql_host:   # Python Script
      import fme
      import json
      
      data = json.load(open('../../config/mssql.json'))
      
      return data['host']

Writers:
- TEXTLINE_1: TEXTLINE to $(DestDataset_TEXTLINE_3)

Creator
    GEOMTYPE = Geometry Object
    NUM = 1
    CREATED -> SQLExecutor_4 [INITIATOR]
    CREATED -> SQLExecutor_2 [INITIATOR]
Note: Get metadata program
SQLExecutor_2
    MSSQL_ADO_COMMAND_TIMEOUT = 30
    SQL_STATEMENT:
      select
      prg.lokalid,
      prg.navn as programNavn,
      Replace (Replace (REPLACE(prg.beskrivelse,'"',''), CHAR(10), ''), CHAR(13), '') as programBeskrivelse
      from
      nin_eier.PROGRAM prg
    COMBINE_ATTRS = Result Attributes Only
    MSSQL_ADO_PASSWORD = $(config_mssql_pass)
    COMBINE_GEOM = Initiator Geometry Only
    DATASET = $(config_mssql_db)
    MSSQL_ADO_SERVER = $(config_mssql_host)
    MSSQL_ADO_USE_SSPI = NO
    MSSQL_ADO_USER_NAME = $(config_mssql_user)
    EXPOSED_ATTRIBUTE_LIST = lokalid,programNavn,programBeskrivelse
    MSSQL_ADO_QUERY_FEATURE_TYPES_FOR_MERGE_FILTERS = Yes
    FORMAT = MSSQL_ADO
    MSSQL_ADO_ENCRYPT_CONNECTION = NO
    RESULT -> JSONTemplater_3 [ROOT]
Note: Get metadata project
SQLExecutor_4
    MSSQL_ADO_COMMAND_TIMEOUT = 30
    SQL_STATEMENT:
      select
      --prj.lokalid,
      prj.prosjektnavn,
      Replace (Replace (REPLACE(prj.prosjektbeskrivelse,'"',''), CHAR(10), ''), CHAR(13), '') as prosjektBeskrivelse,
      prj.programFKID as lokalid
      from
      nin_eier.PROSJEKT prj
    COMBINE_ATTRS = Result Attributes Only
    MSSQL_ADO_PASSWORD = $(config_mssql_pass)
    COMBINE_GEOM = Initiator Geometry Only
    DATASET = $(config_mssql_db)
    MSSQL_ADO_SERVER = $(config_mssql_host)
    MSSQL_ADO_USE_SSPI = NO
    MSSQL_ADO_USER_NAME = $(config_mssql_user)
    EXPOSED_ATTRIBUTE_LIST = lokalid,prosjektnavn,prosjektBeskrivelse
    MSSQL_ADO_QUERY_FEATURE_TYPES_FOR_MERGE_FILTERS = Yes
    FORMAT = MSSQL_ADO
    MSSQL_ADO_ENCRYPT_CONNECTION = NO
    RESULT -> JSONTemplater_4 [ROOT]
JSONTemplater_4
    ROOT_QUERY_EXPR:
      {
          "navn": fme:get-attribute("prosjektnavn"),
          "beskrivelse": fme:get-attribute("prosjektBeskrivelse")
      }
    VISIBLE_QUERY_VALIDATE = Yes
    RESULT_ATTRIBUTE = json
    -> ListBuilder_2
ListBuilder_2
    LIST_NAME = _list
    GROUP_BY = lokalid
    LIST_ATTRS_TO_INCLUDE = json
    GROUPS_ORDERED = No
    -> JSONTemplater_3 [PRJ]
JSONTemplater_3
    ROOT_QUERY_EXPR:
      {
          "program": {
              "navn": fme:get-attribute("programNavn"),
              "beskrivelse": fme:get-attribute("programBeskrivelse"),
              "prosjekter": [fme:process-features("PRJ")]
          }
      }
    VISIBLE_QUERY_VALIDATE = Yes
    GROUP_BY = lokalid
    RESULT_ATTRIBUTE = metadata
    PRJ_QUERY_EXPR = {fme:get-json-list-attribute("_list{}.json")}
    CONSECUTIVE_GROUPS = No
    -> ListBuilder
ListBuilder
    LIST_NAME = _list
    LIST_ATTRS_TO_INCLUDE = metadata
    GROUPS_ORDERED = No
    -> JSONTemplater_2 [ROOT]
Note: Merge all JSON to one file
JSONTemplater_2
    ROOT_QUERY_EXPR = {[fme:get-json-list-attribute("_list{}.metadata")]}
    VISIBLE_QUERY_VALIDATE = Yes
    RESULT_ATTRIBUTE = metadata
    -> text_line (writer TEXTLINE_1)
text_line (writer TEXTLINE_1)
    attributes: text_line_data buffer
