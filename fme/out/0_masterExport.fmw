FME workspace 0_masterExport.fmw

Parameters:
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_host:   # Python Script
      import fme
      import json
      
      data = json.load(open('../../config/postgis.json'))
      
      return data['host']

Creator
    GEOMTYPE = Geometry Object
    NUM = 1
    CREATED -> SQLExecutor [INITIATOR]
SQLExecutor
    COMBINE_ATTRS = Result Attributes Only
    COMBINE_GEOM = Initiator Geometry Only
    DATASET = $(config_db)
    EXPOSED_ATTRIBUTE_LIST = datasetid,prefix
    FORMAT = POSTGRES
    POSTGRES_HOST = $(config_host)
    POSTGRES_PASSWORD = $(config_pass)
    POSTGRES_PORT = 5432
    POSTGRES_QUERY_FEATURE_TYPES_FOR_MERGE_FILTERS = Yes
    POSTGRES_READ_TIME_WITH_TIMEZONE = Yes
    POSTGRES_USER_NAME = $(config_user)
    SQL_STATEMENT:
      select d.id as datasetid, p.value as prefix
      from
      data.dataset d,
      data.prefix p
      where
      p.id = d.prefix_id
    RESULT -> WorkspaceRunner
WorkspaceRunner
    BLOCKING = No
    MAX_PROC = 7
    MAX_TO_BATCH = 1
    WORKSPACE_FILE = $(FME_MF_DIR)01_sqrt42.fmw
    WORKSPACE_PARAMETERS = DestDataset_GEOJSON,D:\out\geojson,mergeNeighbours,true,DestDataset_PNGRASTER,D:\out\raster,datasetId,@Value(datasetid),prefix,@Value(prefix),DestDataset_TEXTLINE_3,D:\out\raster
    SUCCEEDED -> WorkspaceRunner_Failed
    FAILED -> WorkspaceRunner_Failed
    SUMMARY -> WorkspaceRunner_Failed
WorkspaceRunner_Failed: Logger
    LOG_FEATURE = LOG_ONLY
    MAXCOORDS = 20
    MAXFEATS = 20
    MESSAGE = Feature is:
    SEVERITY = INFO
