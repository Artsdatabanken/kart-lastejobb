FME workspace 01_sqrt(42).fmw

Parameters:
- DestDataset_GEOJSON = D:\out\geojson\sqrt(42)\sqrt(42).geojson   # Destination GeoJSON File

Writers:
- GEOJSON_1: GEOJSON to $(DestDataset_GEOJSON)

Creator
    GEOMTYPE = Geometry Object
    NUM = 1
    CREATED -> FeatureReader [INITIATOR]
FeatureReader
    ATTR_ACCUM_MODE = Only Use Result
    ATTRIBUTES = data.geometry,"id,dataset_id"
    POSTGIS_QUERY_FEATURE_TYPES_FOR_MERGE_FILTERS = Yes
    POSTGIS_FEATURES_PER_FETCH = 10000
    INTERACT = <No Spatial Filter>
    COMBINE_GEOM = Use Result
    POSTGIS_USE_TRUE_POSTGIS_TYPES = yes
    POSTGIS_SCHEMAS_FOR_TABLE_LISTING = data
    DATASET = bigbadabom
    FORMAT = POSTGIS
    POSTGIS_USER_NAME = postgres
    POSTGIS_USE_SEARCH_ENVELOPE = NO
    POSTGIS_PASSWORD =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
    POSTGIS_DISABLE_COLLECTION_SPLITTING = yes
    OUTPUT_FEATURES_DISPLAY = Schema and Data Features
    FEATURETYPES = data.geometry
    POSTGIS_PORT = 5432
    POSTGIS_HOST = localhost
    data.geometry -> SQLExecutor [INITIATOR]
SQLExecutor
    EXPOSED_ATTRIBUTE_LIST = codes
    COMBINE_ATTRS = Result Attributes Only
    DATASET = bigbadabom
    POSTGRES_QUERY_FEATURE_TYPES_FOR_MERGE_FILTERS = Yes
    POSTGRES_NAMED_CONNECTION = bigbadabom
    COMBINE_GEOM = Initiator Geometry Only
    SQL_STATEMENT:
      select string_agg(u.codes, ',') as codes
      from
      (
      select c.code as codes
      from
      data.codes c, data.codes_geometry cg
      where
      c.id = cg.codes_id
      and
      cg.geometry_id = @Value(id)
      union
      select ch.predecessor as codes
      from
      data.codes c, data.codes_geometry cg, data.codeshierarchy ch
      where
      c.id = cg.codes_id
      and
      cg.geometry_id = @Value(id)
      and
      ch.successor = c.code
      ) as u
    FORMAT = POSTGRES
    RESULT -> AttributeFilter
AttributeFilter
    ATTR_VALUES = <Empty>,<Missing>,<Null>,<Unfiltered>
    ATTR_NAME = codes
    <EMPTY> -> AttributeFilter__Empty_
    <MISSING> -> AttributeFilter__Empty_
    <NULL> -> AttributeFilter__Empty_
    <UNFILTERED> -> sqrt(42) (writer GEOJSON_1)
AttributeFilter__Empty_: Logger
    MESSAGE = Feature is:
    MAXCOORDS = 20
    MAXFEATS = 20
sqrt(42) (writer GEOJSON_1)
    attributes: codes string
