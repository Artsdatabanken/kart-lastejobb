FME workspace 07_raster_all.fmw

Parameters:
- DestDataset_PNGRASTER = D:\out\raster\codes   # Destination PNG (Portable Network Graphics) Folder
- DestDataset_MBTILES = D:\out\mbtiles\codes   # Destination MBTiles Folder
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_port:   # Python Script
      import fme
      import json
      
      data = json.load(open('../../config/postgis.json'))
      
      return data['port']
- config_host:   # Python Script
      import fme
      import json
      
      data = json.load(open('../../config/postgis.json'))
      
      return data['host']

Writers:
- PNGRASTER_1: PNGRASTER to $(DestDataset_PNGRASTER)
- MBTILES_1: MBTILES to $(DestDataset_MBTILES)

Creator
    GEOMTYPE = Geometry Object
    NUM = 1
    CREATED -> FeatureReader_2 [INITIATOR]
Note: Geometry
FeatureReader_2
    ATTR_ACCUM_MODE = Only Use Result
    POSTGIS_PORT = $(config_port)
    POSTGIS_FEATURES_PER_FETCH = 10000
    INTERACT = <No Spatial Filter>
    POSTGIS_QUERY_FEATURE_TYPES_FOR_MERGE_FILTERS = Yes
    OUTPUT_FEATURES_DISPLAY = Schema and Data Features
    POSTGIS_HOST = $(config_host)
    FEATURETYPES = data.geometry
    POSTGIS_USE_TRUE_POSTGIS_TYPES = yes
    POSTGIS_PASSWORD = $(config_pass)
    POSTGIS_DISABLE_COLLECTION_SPLITTING = yes
    POSTGIS_USE_SEARCH_ENVELOPE = NO
    ATTRS_TO_EXPOSE = id
    POSTGIS_USER_NAME = $(config_user)
    DATASET = $(config_db)
    FORMAT = POSTGIS
    COMBINE_GEOM = Use Result
    <OTHER> -> DatabaseJoiner
DatabaseJoiner
    POSTGRES_QUERY_FEATURE_TYPES_FOR_MERGE_FILTERS = Yes
    FORMAT = POSTGRES
    POSTGRES_HOST = $(config_host)
    MATCH_RULE_DISPLAY = Match All (1:M)
    ADDED_FIELDS = code
    PREFETCH_EXHAUSTIVE = Yes
    POSTGRES_USER_NAME = $(config_user)
    ATTR_ACCUM_MODE = Merge Joined
    JOIN_KEYS = id geometry_id
    MATCH_MULTIPLE_DISPLAY = Create a feature for each match
    POSTGRES_PORT = $(config_port)
    CACHE_SIZE = 5000
    POSTGRES_PASSWORD = $(config_pass)
    DATASET = $(config_db)
    ATTR_CONFLICT_RES = Use Original
    TABLE = data.codes_geometry
    JOINED -> Reprojector
Reprojector
    SOURCE = EPSG:4326
    INTERPOLATION_TYPE_NAME = Nearest Neighbor
    DEST = EPSG:3857
    RASTER_CELL_SIZE = Preserve Cells
    REPROJECTED -> Sorter
Sorter
    SORT_PARM = code ALPHA ASCENDING
    SORTED -> 3DForcer
3DForcer
    KEEPZVAL = No
    ZVALATTR = 255
    -> NumericRasterizer
NumericRasterizer
    SPECIFY_GROUND_EXTENTS = Use input data ground extents
    BACKGROUND_VALUE = 0
    ANTI_ALIASING = No
    Y_CELL_SIZE = 100
    ROWCOL_OR_CELLSIZE = CellSize
    FILL_WITH_NODATA = Yes
    INTERPRETATION_TYPE = UInt8
    GROUP_BY = code
    TOLERANCE = 0.5
    X_CELL_SIZE = 100
    RASTER -> RasterInterpretationCoercer [off]
    RASTER -> RasterInterpretationCoercer_2
RasterInterpretationCoercer
    COLOR_TO_COLOR = Cast
    INTERPRETATION = Gray8
    NUMERIC_TO_COLOR = Cast
    FLOAT_TO_INTEGER = Round
    -> Raster1 (writer PNGRASTER_1)
Raster1 (writer PNGRASTER_1)
    attributes: code char(200)
RasterInterpretationCoercer_2
    COLOR_TO_COLOR = Cast
    INTERPRETATION = Blue8
    NUMERIC_TO_COLOR = Cast
    FLOAT_TO_INTEGER = Round
    -> Raster1 (writer MBTILES_1)
Raster1 (writer MBTILES_1)
