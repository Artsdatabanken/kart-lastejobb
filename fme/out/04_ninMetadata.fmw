FME workspace 04_ninMetadata.fmw

Parameters:
- DestDataset_TEXTLINE_3 = D:\out\json\ninMetadata   # Destination Text File
- DestDataset_TEXTLINE = D:\out\json\ninMetadata\all.json   # Destination Text File
- config_mssql_pass:   # Python Script
      import fme
      import json
      
      data = json.load(open('../../config/mssql.json'))
      
      return data['pass']
- config_mssql_user:   # Python Script
      import fme
      import json
      
      data = json.load(open('../../config/mssql.json'))
      
      return data['user']
- config_mssql_db:   # Python Script
      import fme
      import json
      
      data = json.load(open('../../config/mssql.json'))
      
      return data['db']
- config_mssql_host:   # Python Script
      import fme
      import json
      
      data = json.load(open('../../config/mssql.json'))
      
      return data['host']
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_port:   # Python Script
      import fme
      import json
      
      data = json.load(open('../../config/postgis.json'))
      
      return data['port']
- config_host:   # Python Script
      import fme
      import json
      
      data = json.load(open('../../config/postgis.json'))
      
      return data['host']

Writers:
- TEXTLINE_1: TEXTLINE to $(DestDataset_TEXTLINE_3)
- TEXTLINE_2: TEXTLINE to $(DestDataset_TEXTLINE)

Creator
    GEOMTYPE = Geometry Object
    NUM = 1
    CREATED -> SQLExecutor_3 [INITIATOR]
    CREATED -> SQLExecutor_2 [INITIATOR]
    CREATED -> SQLExecutor_4 [INITIATOR]
    CREATED -> SQLExecutor_5 [INITIATOR]
Note: Remove invalid keys / Prettify
PythonCaller_2
    PYTHONSOURCE:
      # -*- coding: utf-8 -*-
      import fme
      import fmeobjects
      import json
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
      #        codes='codes'
              metadata = json.loads(feature.getAttribute('metadata'))
      #        nyeKoder = []
      #        for koder in metadata[codes]:
      #            if type(koder) is dict:
      #                for kode in koder:
      #                    if kode != "":
      #                        nyeKoder.append(koder[kode])
      #            else:
      #                nyeKoder=metadata[codes][koder]
      #        metadata.pop(codes, None)
      #        if len(nyeKoder) > 0:
      #            metadata[codes] = nyeKoder
              feature.setAttribute('metadata', json.dumps(metadata,  indent=2, ensure_ascii=False))
              self.pyoutput(feature)
          def close(self):
              pass
    PYTHONSYMBOL = FeatureProcessor
    -> text_line (writer TEXTLINE_1)
Note: Remove invalid keys / Prettify
PythonCaller_3
    PYTHONSOURCE:
      # -*- coding: utf-8 -*-
      import fme
      import fmeobjects
      import json
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              #codes='codes'
              metadata = json.loads(feature.getAttribute('metadata'))
              #for lokalid in metadata:
              #    nyeKoder = {}
              #    for koder in metadata[lokalid][codes]:
              #        if type(koder) is dict:
              #            for kode in koder:
              #                if kode != "":
              #                    nyeKoder[kode] = koder[kode]
              #        else:
              #            nyeKoder[koder] = metadata[lokalid][codes][koder]
              #    metadata[lokalid].pop(codes, None)
              #    if len(nyeKoder.keys()) > 0:
              #        metadata[lokalid][codes] = nyeKoder
              feature.setAttribute('metadata', json.dumps(metadata,  indent=2, ensure_ascii=False))
              self.pyoutput(feature)
          def close(self):
              pass
    PYTHONSYMBOL = FeatureProcessor
    -> text_line (writer TEXTLINE_2)

Bookmark: Metadata
Note: Get metadata
SQLExecutor_4
    MSSQL_ADO_QUERY_FEATURE_TYPES_FOR_MERGE_FILTERS = Yes
    MSSQL_ADO_PASSWORD = $(config_mssql_pass)
    MSSQL_ADO_ENCRYPT_CONNECTION = NO
    COMBINE_GEOM = Initiator Geometry Only
    MSSQL_ADO_SERVER = $(config_mssql_host)
    MSSQL_ADO_USER_NAME = $(config_mssql_user)
    FORMAT = MSSQL_ADO
    MSSQL_ADO_COMMAND_TIMEOUT = 30
    MSSQL_ADO_USE_SSPI = NO
    COMBINE_ATTRS = Result Attributes Only
    SQL_STATEMENT:
      select
      --top 10
      nom.brukernavn,
      nom.lokalid,
      Replace (Replace (REPLACE(nom.beskrivelse,'"',''), CHAR(10), ''), CHAR(13), '') as naturområdeBeskrivelse,
      prj.prosjektnavn,
      Replace (Replace (REPLACE(prj.prosjektbeskrivelse,'"',''), CHAR(10), ''), CHAR(13), '') as prosjektBeskrivelse,
      prg.navn as programNavn,
      Replace (Replace (REPLACE(prg.beskrivelse,'"',''), CHAR(10), ''), CHAR(13), '') as programBeskrivelse,
      nom.kartleggingsMaalestokk as surveyScale
      from
      nin_eier.NATUROMRAADE nom,
      nin_eier.PROSJEKT prj,
      nin_eier.PROGRAM prg
      where
      nom.prosjektFKID = prj.lokalid
      and
      prj.programFKID = prg.lokalid
    EXPOSED_ATTRIBUTE_LIST = lokalid,brukernavn,naturområdeBeskrivelse,prosjektnavn,prosjektBeskrivelse,programNavn,programBeskrivelse,surveyScale
    DATASET = $(config_mssql_db)
    RESULT -> FeatureMerger_2 [REQUESTOR]
Note: Get surveyor
SQLExecutor_5
    MSSQL_ADO_QUERY_FEATURE_TYPES_FOR_MERGE_FILTERS = Yes
    MSSQL_ADO_PASSWORD = $(config_mssql_pass)
    MSSQL_ADO_ENCRYPT_CONNECTION = NO
    COMBINE_GEOM = Initiator Geometry Only
    MSSQL_ADO_SERVER = $(config_mssql_host)
    MSSQL_ADO_USER_NAME = $(config_mssql_user)
    FORMAT = MSSQL_ADO
    MSSQL_ADO_COMMAND_TIMEOUT = 30
    MSSQL_ADO_USE_SSPI = NO
    COMBINE_ATTRS = Result Attributes Only
    SQL_STATEMENT:
      select
      --top 10
      b.navn,
      b.brukernavn,
      b.firmaNavn as firma,
      b.email,
      b.hjemmeside
      from
      nin_eier.BRUKER b
    EXPOSED_ATTRIBUTE_LIST = brukernavn,firma,email,hjemmeside,navn
    DATASET = $(config_mssql_db)
    RESULT -> FeatureMerger_2 [SUPPLIER]
FeatureMerger_2
    SUPPLIERS_FIRST = No
    ATTR_CONFLICT_RES = Use Requestor
    IGNORE_NULLS = No
    ATTR_ACCUM_MODE = Merge Supplier
    MERGE_TYPE = Attributes Only
    JOIN_KEYS = @Value(brukernavn) @Value(brukernavn) STRING
    REJECT_NULL_MISSING_KEYS = No
    PROCESS_DUPS = No
    MERGED -> FeatureMerger [REQUESTOR]
    UNMERGED_REQUESTOR -> FeatureMerger [REQUESTOR]

Bookmark: Natruområdetype
Note: Get naturområdetype
SQLExecutor_2
    MSSQL_ADO_QUERY_FEATURE_TYPES_FOR_MERGE_FILTERS = Yes
    MSSQL_ADO_PASSWORD = $(config_mssql_pass)
    MSSQL_ADO_ENCRYPT_CONNECTION = NO
    COMBINE_GEOM = Initiator Geometry Only
    MSSQL_ADO_SERVER = $(config_mssql_host)
    MSSQL_ADO_USER_NAME = $(config_mssql_user)
    FORMAT = MSSQL_ADO
    MSSQL_ADO_COMMAND_TIMEOUT = 30
    MSSQL_ADO_USE_SSPI = NO
    COMBINE_ATTRS = Result Attributes Only
    SQL_STATEMENT:
      select
      nat.naturomraadeFKID as lokalid,
      nat.lokalid as naturområdetypeLokalid,
      nat.kode,
      nat.andel
      from
      nin_eier.NATUROMRAADETYPE nat

      --where nat.naturomraadeFKID = '11E90AB5-A737-4458-BE82-31CB61B71927'
    EXPOSED_ATTRIBUTE_LIST = kode,naturområdetypeLokalid,andel,lokalid
    DATASET = $(config_mssql_db)
    RESULT -> AttributeFilter_2
AttributeFilter_2
    ATTR_VALUES = <Empty>,<Missing>,<Null>,<Unfiltered>
    ATTR_NAME = andel
    <EMPTY> -> AttributeManager
    <MISSING> -> AttributeManager
    <NULL> -> AttributeManager
    <UNFILTERED> -> AttributeFilter
AttributeManager
    ATTR_TABLE = SET_TO andel = 10
    -> AttributeFilter
AttributeFilter
    ATTR_VALUES = <Empty>,<Missing>,<Null>,<Unfiltered>
    ATTR_NAME = kode
    <EMPTY> -> AttributeFilter__Empty_
    <MISSING> -> AttributeFilter__Empty_
    <NULL> -> AttributeFilter__Empty_
    <UNFILTERED> -> AttributeTrimmer
AttributeTrimmer
    TRIM_TYPE = Both
    TRIM_CHARS = " "
    TRIM_TO_NONE = Yes
    SRC_ATTRS = kode
    -> SQLExecutor_8 [INITIATOR]
SQLExecutor_8
    POSTGRES_USER_NAME = $(config_user)
    COMBINE_GEOM = Initiator Geometry Only
    POSTGRES_QUERY_FEATURE_TYPES_FOR_MERGE_FILTERS = Yes
    POSTGRES_PASSWORD = $(config_pass)
    FORMAT = POSTGRES
    POSTGRES_PORT = $(config_port)
    COMBINE_ATTRS = Keep Result Attributes if Conflict
    POSTGRES_HOST = $(config_host)
    SQL_STATEMENT:
      select c.title as tittel
      from
      data.codes c
      where
      c.code = '@Value(kode)'
    EXPOSED_ATTRIBUTE_LIST = tittel
    DATASET = $(config_db)
    RESULT -> JSONTemplater_3 [ROOT]
AttributeFilter__Empty_: Logger
    MESSAGE = Feature is:
    MAXCOORDS = 20
    MAXFEATS = 20

Bookmark: Beskrivelsesvariabler
Note: Get beskrivelsesvariabler / Filters out those that ends in '-x' and '-XY' / Filters out variabelGruppe 'Mdir' and 'uLKM'
SQLExecutor_3
    MSSQL_ADO_QUERY_FEATURE_TYPES_FOR_MERGE_FILTERS = Yes
    MSSQL_ADO_PASSWORD = $(config_mssql_pass)
    MSSQL_ADO_ENCRYPT_CONNECTION = NO
    COMBINE_GEOM = Initiator Geometry Only
    MSSQL_ADO_SERVER = $(config_mssql_host)
    MSSQL_ADO_USER_NAME = $(config_mssql_user)
    FORMAT = MSSQL_ADO
    MSSQL_ADO_COMMAND_TIMEOUT = 30
    MSSQL_ADO_USE_SSPI = NO
    COMBINE_ATTRS = Result Attributes Only
    SQL_STATEMENT:
      select --top 10000
      bv.omraadetypeFKID as naturområdetypeLokalid,
      bv.kode as beskrivelsesvariabel
      from
      nin_eier.BESKRIVELSESVARIABEL bv
      where
      bv.kode not like '%-XY'
      and
      bv.kode not like '%-x'
      and
      bv.variabelGruppe not in ('Mdir', 'uLKM')
    EXPOSED_ATTRIBUTE_LIST = naturområdetypeLokalid,beskrivelsesvariabel
    DATASET = $(config_mssql_db)
    RESULT -> AttributeSplitter
AttributeSplitter
    TRIM_OPTION = Both
    LIST_NAME = _list
    DELIMITER = ,
    DROP_EMPTY_PARTS = No
    ATTR_NAME = beskrivelsesvariabel
    -> ListExploder
ListExploder
    ATTR_CONFLICT_RES = Use List Attribute Values
    LIST_ATTR = _list{}
    INDEX_ATTR = _element_index
    ATTR_ACCUM_MODE = Merge List Attributes
    ELEMENTS -> AttributeRenamer
AttributeRenamer
    ATTR_TABLE = RENAME_SET_DEFAULT _list > beskrivelsesvariabel
    -> AttributeCreator
AttributeCreator
    ATTR_TABLE = SET_TO beskrivelsesvariabel = BS_@Value(beskrivelsesvariabel)
    -> SQLExecutor_9 [INITIATOR]
Note: Get titles / TODO: Find out why some go missing here
SQLExecutor_9
    POSTGRES_USER_NAME = $(config_user)
    COMBINE_GEOM = Initiator Geometry Only
    POSTGRES_QUERY_FEATURE_TYPES_FOR_MERGE_FILTERS = Yes
    POSTGRES_PASSWORD = $(config_pass)
    FORMAT = POSTGRES
    POSTGRES_PORT = $(config_port)
    COMBINE_ATTRS = Keep Result Attributes if Conflict
    POSTGRES_HOST = $(config_host)
    SQL_STATEMENT:
      select c.title as tittel
      from
      data.codes c
      where
      c.code = '@Value(beskrivelsesvariabel)'
    EXPOSED_ATTRIBUTE_LIST = tittel
    DATASET = $(config_db)
    RESULT -> PythonCaller_4
    <REJECTED> -> SQLExecutor_9__Rejected_
SQLExecutor_9__Rejected_: Inspector
Note: Find codes that need an explanation
PythonCaller_4
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              code = feature.getAttribute('beskrivelsesvariabel')
              if(len(code.split("_")) < 3):
                  feature.setAttribute('parentCode', None)
                  self.pyoutput(feature)
              else:
                  parentCode = code.split("_")[0] + '_' + code.split("_")[1]
                  feature.setAttribute('parentCode', parentCode)
                  self.pyoutput(feature)
          def close(self):
              pass
    PYTHONSYMBOL = FeatureProcessor
    NEW_ATTRIBUTES = parentCode
    -> AttributeFilter_4
AttributeFilter_4
    ATTR_VALUES = <Empty>,<Missing>,<Null>,<Unfiltered>
    ATTR_NAME = parentCode
    <EMPTY> -> JSONTemplater_5 [ROOT]
    <EMPTY> -> AttributeFilter_4__Empty_
    <UNFILTERED> -> SQLExecutor_10 [INITIATOR]
SQLExecutor_10
    POSTGRES_USER_NAME = $(config_user)
    COMBINE_GEOM = Initiator Geometry Only
    POSTGRES_QUERY_FEATURE_TYPES_FOR_MERGE_FILTERS = Yes
    POSTGRES_PASSWORD = $(config_pass)
    FORMAT = POSTGRES
    POSTGRES_PORT = $(config_port)
    COMBINE_ATTRS = Keep Result Attributes if Conflict
    POSTGRES_HOST = $(config_host)
    SQL_STATEMENT:
      select
      c.title as parent
      from
      data.codes c
      where
      c.code = '@Value(parentCode)'
    EXPOSED_ATTRIBUTE_LIST = parent
    DATASET = $(config_db)
    RESULT -> JSONTemplater_4 [ROOT]
JSONTemplater_4
    VISIBLE_QUERY_VALIDATE = Yes
    RESULT_ATTRIBUTE = beskrivelsesvariabler
    CONSECUTIVE_GROUPS = No
    ROOT_QUERY_EXPR:
      {
          fme:get-attribute("beskrivelsesvariabel"): {
              "tittel": fme:get-attribute("tittel"),
              "forfader": fme:get-attribute("parent")
              }
      }
    GROUP_BY = naturområdetypeLokalid
    -> ListBuilder_2
JSONTemplater_5
    VISIBLE_QUERY_VALIDATE = Yes
    RESULT_ATTRIBUTE = beskrivelsesvariabler
    CONSECUTIVE_GROUPS = No
    ROOT_QUERY_EXPR:
      {
          fme:get-attribute("beskrivelsesvariabel"): {
              "tittel": fme:get-attribute("tittel")
              }
      }
    GROUP_BY = naturområdetypeLokalid
    -> ListBuilder_2
ListBuilder_2
    GROUPS_ORDERED = No
    LIST_ATTRS_TO_INCLUDE = beskrivelsesvariabler
    LIST_NAME = _list
    GROUP_BY = naturområdetypeLokalid
    -> JSONTemplater_3 [KODER]
AttributeFilter_4__Empty_: Inspector

Bookmark: Join beskrivelsesvariabler with naturområdetyper
JSONTemplater_3
    KODER_QUERY_EXPR = {fme:get-json-list-attribute("_list{}.beskrivelsesvariabler")}
    VISIBLE_QUERY_VALIDATE = Yes
    RESULT_ATTRIBUTE = koder
    CONSECUTIVE_GROUPS = No
    ROOT_QUERY_EXPR:
      {
          fme:get-attribute("kode"): {
              "andel": fme:get-attribute("andel"),
              "tittel": fme:get-attribute("tittel"),
              "beskrivelsesvariabler": fme:process-features("KODER")
          }
      }
    GROUP_BY = naturområdetypeLokalid
    -> ListBuilder_3
ListBuilder_3
    GROUPS_ORDERED = No
    LIST_ATTRS_TO_INCLUDE = koder naturområdetypeLokalid
    LIST_NAME = koder_list
    GROUP_BY = lokalid
    -> FeatureMerger [SUPPLIER]

Bookmark: Join all data and minor tidying
FeatureMerger
    SUPPLIERS_FIRST = No
    ATTR_CONFLICT_RES = Use Requestor
    IGNORE_NULLS = No
    ATTR_ACCUM_MODE = Merge Supplier
    MERGE_TYPE = Attributes Only
    JOIN_KEYS = @Value(lokalid) @Value(lokalid) AUTO
    REJECT_NULL_MISSING_KEYS = No
    PROCESS_DUPS = No
    MERGED -> StringReplacer
    UNMERGED_REQUESTOR -> FeatureMerger_UnmergedRequestor
    UNUSED_SUPPLIER -> FeatureMerger_UnmergedRequestor
StringReplacer
    FIND_TEXT = {
    NO_MATCH = _FME_NO_OP_
    CASE = NO
    REGEXP = NO
    SRC_ATTRS = lokalid
    -> StringReplacer_2
StringReplacer_2
    FIND_TEXT = }
    NO_MATCH = _FME_NO_OP_
    CASE = NO
    REGEXP = NO
    SRC_ATTRS = lokalid
    -> AttributeValueMapper
Note: SurveyScale is just guessed here
AttributeValueMapper
    DIRECTION = Forward (Source To Destination)
    LUT = 3,1:5000,FME_NULL_VALUE,1:20000
    SRC = surveyScale
    VAL_ATTR = surveyScale
    -> JSONTemplater_6 [SUB]
    -> JSONTemplater_6 [ROOT]
Note: Build JSON per lokalid / Adds hardcoded owner
JSONTemplater_6
    SUB_QUERY_EXPR = {fme:get-json-list-attribute("koder_list{}.koder")}
    VISIBLE_QUERY_VALIDATE = Yes
    RESULT_ATTRIBUTE = metadata
    CONSECUTIVE_GROUPS = No
    ROOT_QUERY_EXPR:
      {
          "description": fme:get-attribute("naturområdeBeskrivelse"),
          "surveyer": {
              "company": fme:get-attribute("firma"),
              "contactPerson" : fme:get-attribute("navn"),
              "email": fme:get-attribute("email"),
              "homepage": fme:get-attribute("hjemmeside")
          },
         "owner": {
              "company": "Miljødirektoratet",
              "contactPerson": "kjepet (Kjetil Pettersson)",
              "email": "kjetil.pettersson@miljodir.no",
              "homepage": "http://www.miljodirektoratet.no"
          },
          "program": {
              "name": fme:get-attribute("programNavn"),
              "description":  fme:get-attribute("programBeskrivelse")
          },
          "project":{
              "name": fme:get-attribute("prosjektnavn"),
              "description":  fme:get-attribute("prosjektBeskrivelse")
          },
          "surveyScale": fme:get-attribute("surveyScale"),
          "codes": fme:process-features("SUB")
      }
    GROUP_BY = koder_list{0}.naturområdetypeLokalid
    -> PythonCaller_2 [off]
    -> JSONTemplater [ROOT]
    -> text_line (writer TEXTLINE_1)
FeatureMerger_UnmergedRequestor: Logger
    MESSAGE = Feature is:
    MAXCOORDS = 20
    MAXFEATS = 20

Bookmark: Individual json pr naturområde
text_line (writer TEXTLINE_1)
    attributes: text_line_data buffer

Bookmark: Single json-file
Note: Adds localid-key
JSONTemplater
    VISIBLE_QUERY_VALIDATE = Yes
    RESULT_ATTRIBUTE = metadata
    ROOT_QUERY_EXPR:
      {fme:get-attribute("lokalid"):
          fme:get-json-attribute("metadata")
      }
    -> ListBuilder
ListBuilder
    GROUPS_ORDERED = No
    LIST_ATTRS_TO_INCLUDE = lokalid metadata
    LIST_NAME = _list
    -> JSONTemplater_2 [ROOT]
Note: Merge all JSON to one file
JSONTemplater_2
    VISIBLE_QUERY_VALIDATE = Yes
    RESULT_ATTRIBUTE = text_line_data
    ROOT_QUERY_EXPR = {[fme:get-json-list-attribute("_list{}.metadata")]}
    -> PythonCaller_3
    -> text_line (writer TEXTLINE_2)
text_line (writer TEXTLINE_2)
    attributes: text_line_data buffer
