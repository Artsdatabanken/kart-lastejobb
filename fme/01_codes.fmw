FME workspace 01_codes.fmw

Parameters:
- SourceDataset_JSON = https://firebasestorage.googleapis.com/v0/b/grunnkart.appspot.com/o/koder%2Fkoder_med_forfedre.json?alt=media   # Source JSON (JavaScript Object Notation) File or URL
- config_db:   # Python Script
      import fme
      import json
      
      data = json.load(open('../config/postgis.json'))
      
      return data['db']

Readers:
- JSON_1: JSON from $(SourceDataset_JSON)

Writers:
- POSTGIS_1: POSTGIS to $(config_db)

JSONFeature (reader JSON_1)
    attributes: meta.tittel string, meta.produsert string, meta.utgiver string, meta.url string, meta.elementer int, data{}.kode string, data{}.forfedre{} string, data{}.tittel string
    -> ListExploder
ListExploder
    LIST_ATTR = data{}
    ATTR_ACCUM_MODE = Merge List Attributes
    INDEX_ATTR = _element_index
    ATTR_CONFLICT_RES = Use List Attribute Values
    ELEMENTS -> ListExploder_2
    ELEMENTS -> AttributeRenamer_2
    <REJECTED> -> ListExploder__Rejected_
ListExploder_2
    LIST_ATTR = forfedre{}
    ATTR_ACCUM_MODE = Merge List Attributes
    INDEX_ATTR = _element_index_forfedre
    ATTR_CONFLICT_RES = Use List Attribute Values
    ELEMENTS -> AttributeKeeper
    <REJECTED> -> ListExploder_2__Rejected_
AttributeKeeper
    KEEP_ATTRS = tittel,_element_index_forfedre,forfedre,kode,_element_index
    -> AttributeRenamer
AttributeRenamer
    ATTR_TABLE:
      RENAME_SET_DEFAULT forfedre > predecessor
      RENAME_SET_DEFAULT kode > successor
    -> data.codeshierarchy (writer POSTGIS_1)
data.codeshierarchy (writer POSTGIS_1)
    attributes: predecessor text, successor text
ListExploder_2__Rejected_: Logger
    MAXCOORDS = 20
    MAXFEATS = 20
    MESSAGE = Feature is:
AttributeRenamer_2
    ATTR_TABLE:
      RENAME_SET_DEFAULT kode > code
      RENAME_SET_DEFAULT tittel > title
    -> DuplicateFilter
DuplicateFilter
    KEYATTR = title code
    INPUT_ORDERED_CHOICE = No
    UNIQUE -> codes (writer POSTGIS_1)
codes (writer POSTGIS_1)
    attributes: code text, title text
ListExploder__Rejected_: Logger
    MAXCOORDS = 20
    MAXFEATS = 20
    MESSAGE = Feature is:
