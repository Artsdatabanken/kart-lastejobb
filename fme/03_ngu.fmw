FME workspace 03_ngu.fmw

Parameters:
- SourceDataset_FILEGDB_3 = D:\in\NGU\NGU_utkast_01.gdb   # File Geodatabase
- config_pass:   # Python Script
      import fme
      import json
      
      data = json.load(open('../config/postgis.json'))
      
      return data['pass']
- config_user:   # Python Script
      import fme
      import json
      
      data = json.load(open('../config/postgis.json'))
      
      return data['user']
- config_db:   # Python Script
      import fme
      import json
      
      data = json.load(open('../config/postgis.json'))
      
      return data['db']
- config_port:   # Python Script
      import fme
      import json
      
      data = json.load(open('../config/postgis.json'))
      
      return data['port']
- config_host:   # Python Script
      import fme
      import json
      
      data = json.load(open('../config/postgis.json'))
      
      return data['host']
- Dataset = ngu
- Prefix = MI
- PrefixDesc = Miljøvariabel

Readers:
- POSTGRES_1: POSTGRES from $(config_db)
- FILEGDB_1: FILEGDB from $(SourceDataset_FILEGDB_3)

Writers:
- POSTGIS_1: POSTGIS to $(config_db)

NIN_VIEW_BE250_KALK (reader FILEGDB_1)
    attributes: OBJECTID objectid, OBJEKTTYPE text(32), TEGNFORKLARING text(200), HOVEDBERGART smallint, HOVEDBERGART_TEKST text(255), KALKINNHOLD_HOVEDBERGART int, TILLEGGSBERGART1 smallint, TILLEGGSBERGART1_TEKST text(255), KALKINNHOLD_TILLEGSBERGART1 int, TILLEGGSBERGART2 smallint, TILLEGGSBERGART2_TEKST text(255), KALKINNHOLD_TILLEGSBERGART2 int, TILLEGGSBERGART3 smallint, TILLEGGSBERGART3_TEKST text(255), KALKINNHOLD_TILLEGSBERGART3 int, Shape_Length double, Shape_Area double
    -> AttributeKeeper_3
AttributeKeeper_3
    KEEP_ATTRS = KALKINNHOLD_HOVEDBERGART
    -> AttributeValueMapper
AttributeValueMapper
    VAL_ATTR = _looked_up
    DIRECTION = Forward (Source To Destination)
    LUT = 1,$(Prefix)_KA-A,2,$(Prefix)_KA-B,3,$(Prefix)_KA-D,4,$(Prefix)_KA-F,5,$(Prefix)_KA-H
    SRC = KALKINNHOLD_HOVEDBERGART
    -> AttributeRenamer_2
AttributeRenamer_2
    ATTR_TABLE = RENAME_SET_DEFAULT _looked_up > orig_code
    -> Reprojector
NIN_VIEW_BE250_ULTRAMAFISK (reader FILEGDB_1)
    attributes: OBJECTID objectid, OBJEKTTYPE text(32), TEGNFORKLARING text(200), HOVEDBERGART smallint, HOVEDBERGART_TEKST text(255), ULTRAMAFISK text(5), Shape_Length double, Shape_Area double
    -> AttributeKeeper_2
AttributeKeeper_2
    -> AttributeCreator
AttributeCreator
    ATTR_TABLE = SET_TO orig_code = $(Prefix)_BK-A
    -> Reprojector
Reprojector
    DEST = EPSG:4326
    INTERPOLATION_TYPE_NAME = Nearest Neighbor
    SOURCE = Read from feature
    RASTER_CELL_SIZE = Preserve Cells
    REPROJECTED -> Sampler
Sampler
    SAMPLE_TYPE_LONG = First N Features
    RATE = 1
    SAMPLE_MODE = No
    SAMPLED -> SQLExecutor_4 [INITIATOR]
    NOT_SAMPLED -> SQLExecutor_2 [INITIATOR]
Note: Insert prefix and dataset
SQLExecutor_4
    DATASET = $(config_db)
    SQL_STATEMENT:
      INSERT INTO data.prefix (value, description) values ('$(Prefix)', '$(PrefixDesc)');
      INSERT INTO data.dataset (prefix_id, description) Select id, '$(Dataset)' from data.prefix where value = '$(Prefix)';
    COMBINE_GEOM = Initiator Geometry Only
    POSTGRES_USER_NAME = $(config_user)
    POSTGRES_PASSWORD = $(config_pass)
    POSTGRES_PORT = $(config_port)
    POSTGRES_SCHEMAS_FOR_TABLE_LISTING = data
    FORMAT = POSTGRES
    COMBINE_ATTRS = Keep Initiator Attributes if Conflict
    POSTGRES_QUERY_FEATURE_TYPES_FOR_MERGE_FILTERS = Yes
    POSTGRES_HOST = $(config_host)
    INITIATOR -> SQLExecutor_2 [INITIATOR]
Note: Get id for pk
SQLExecutor_2
    DATASET = $(config_db)
    SQL_STATEMENT = SELECT nextval('data.geometry_id_seq') as id
    COMBINE_GEOM = Initiator Geometry Only
    EXPOSED_ATTRIBUTE_LIST = id
    POSTGRES_USER_NAME = $(config_user)
    POSTGRES_PASSWORD = $(config_pass)
    POSTGRES_PORT = $(config_port)
    POSTGRES_SCHEMAS_FOR_TABLE_LISTING = data
    FORMAT = POSTGRES
    COMBINE_ATTRS = Keep Initiator Attributes if Conflict
    POSTGRES_QUERY_FEATURE_TYPES_FOR_MERGE_FILTERS = Yes
    POSTGRES_HOST = $(config_host)
    RESULT -> SQLExecutor [INITIATOR]
    RESULT -> AttributeRenamer_4
Note: Get dataset id
SQLExecutor
    DATASET = bigbadabom
    SQL_STATEMENT = select id from data.dataset where description='$(Dataset)';
    COMBINE_GEOM = Initiator Geometry Only
    EXPOSED_ATTRIBUTE_LIST = dataset_id
    POSTGRES_USER_NAME = postgres
    POSTGRES_PASSWORD =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
    POSTGRES_PORT = 5432
    POSTGRES_SCHEMAS_FOR_TABLE_LISTING = data
    FORMAT = POSTGRES
    COMBINE_ATTRS = Keep Initiator Attributes if Conflict
    POSTGRES_QUERY_FEATURE_TYPES_FOR_MERGE_FILTERS = Yes
    POSTGRES_HOST = localhost
    RESULT -> geometry (writer POSTGIS_1)
geometry (writer POSTGIS_1)
    attributes: dataset_id int8, id int8
AttributeRenamer_4
    ATTR_TABLE = RENAME_SET_DEFAULT id > geometry_id
    -> FeatureHolder
FeatureHolder
    -> FeatureMerger [REQUESTOR]
data.codes (reader POSTGRES_1)
    attributes: id int8,PrimaryKey, code text,BTree, title text
    -> FeatureMerger [SUPPLIER]
Note: Get codes id
FeatureMerger
    IGNORE_NULLS = No
    PROCESS_DUPS = No
    MERGE_TYPE = Attributes Only
    ATTR_ACCUM_MODE = Merge Supplier
    REJECT_NULL_MISSING_KEYS = No
    ATTR_CONFLICT_RES = Use Requestor
    JOIN_KEYS = @Value(orig_code) @Value(code) AUTO
    SUPPLIERS_FIRST = No
    MERGED -> AttributeRenamer_3
    <REJECTED> -> FeatureMerger__Rejected_
AttributeRenamer_3
    ATTR_TABLE = RENAME_SET_DEFAULT id > codes_id
    -> codes_geometry (writer POSTGIS_1)
codes_geometry (writer POSTGIS_1)
    attributes: codes_id text, geometry_id text
FeatureMerger__Rejected_: Logger
    MAXCOORDS = 20
    MAXFEATS = 20
    MESSAGE = Feature is:
