FME workspace 05_kv.fmw

Parameters:
- SourceDataset_GEOJSON = ""D:\in\KV\AdministrativeEnheter\Basisdata_0000_Norge_25833_Fylker_GEOJSON.geojson" "D:\in\KV\AdministrativeEnheter\Basisdata_0000_Norge_25833_Kommuner_GEOJSON.geojson""   # Source GeoJSON File or URL
- config_pass:   # Python Script
      import fme
      import json
      
      data = json.load(open('../config/postgis.json'))
      
      return data['pass']
- config_user:   # Python Script
      import fme
      import json
      
      data = json.load(open('../config/postgis.json'))
      
      return data['user']
- config_db:   # Python Script
      import fme
      import json
      
      data = json.load(open('../config/postgis.json'))
      
      return data['db']
- config_port:   # Python Script
      import fme
      import json
      
      data = json.load(open('../config/postgis.json'))
      
      return data['port']
- config_host:   # Python Script
      import fme
      import json
      
      data = json.load(open('../config/postgis.json'))
      
      return data['host']
- Dataset = ae
- Prefix = NO
- PrefixDesc = AdministrativEnhet

Readers:
- GEOJSON_1: GEOJSON from $(SourceDataset_GEOJSON)

Writers:
- POSTGIS_1: POSTGIS to $(config_db)

administrative_enheter.kommune (reader GEOJSON_1)
    attributes: objid int, objtype string, samiskforvaltningsomrade boolean, lokalid string, navnerom string, versjonid string, datafangstdato string, oppdateringsdato string, datauttaksdato string, opphav string, kommunenummer string, navn{}.navn string, navn{}.rekkefolge string, navn{}.sprak string
    -> AttributeKeeper
AttributeKeeper
    KEEP_ATTRS = kommunenummer
    KEEP_LIST = navn{}
    -> AttributeRenamer_2
AttributeRenamer_2
    ATTR_TABLE = RENAME_SET_DEFAULT kommunenummer > code = $(Prefix)_@Value(kommunenummer)
    -> Sampler
administrative_enheter.fylke (reader GEOJSON_1)
    attributes: objtype string, samiskforvaltningsomrade boolean, lokalid string, navnerom string, versjonid string, datafangstdato string, oppdateringsdato string, datauttaksdato string, opphav string, fylkesnummer string, navn{}.navn string, navn{}.rekkefolge string, navn{}.sprak string
    -> AttributeKeeper_3
AttributeKeeper_3
    KEEP_ATTRS = fylkesnummer
    KEEP_LIST = navn{}
    -> AttributeRenamer_3
AttributeRenamer_3
    ATTR_TABLE = RENAME_SET_DEFAULT kommunenummer > code = $(Prefix)_@Value(fylkesnummer)
    -> Sampler
Sampler
    RATE = 1
    SAMPLE_TYPE_LONG = First N Features
    SAMPLE_MODE = No
    SAMPLED -> SQLExecutor_4 [INITIATOR]
    NOT_SAMPLED -> Reprojector
Note: Insert prefix and dataset
SQLExecutor_4
    DATASET = $(config_db)
    POSTGRES_USER_NAME = $(config_user)
    POSTGRES_PORT = $(config_port)
    POSTGRES_HOST = $(config_host)
    COMBINE_ATTRS = Keep Initiator Attributes if Conflict
    POSTGRES_SCHEMAS_FOR_TABLE_LISTING = data
    FORMAT = POSTGRES
    POSTGRES_PASSWORD = $(config_pass)
    COMBINE_GEOM = Initiator Geometry Only
    SQL_STATEMENT:
      INSERT INTO data.prefix (value, description) values ('$(Prefix)', '$(PrefixDesc)');
      INSERT INTO data.dataset (prefix_id, description) Select id, '$(Dataset)' from data.prefix where value = '$(Prefix)';
    POSTGRES_QUERY_FEATURE_TYPES_FOR_MERGE_FILTERS = Yes
    INITIATOR -> Reprojector
Reprojector
    DEST = EPSG:4326
    RASTER_CELL_SIZE = Preserve Cells
    SOURCE = Read from feature
    INTERPOLATION_TYPE_NAME = Nearest Neighbor
    REPROJECTED -> ListExploder
ListExploder
    INDEX_ATTR = _element_index
    ATTR_ACCUM_MODE = Merge List Attributes
    LIST_ATTR = navn{}
    ATTR_CONFLICT_RES = Use List Attribute Values
    ELEMENTS -> AttributeFilter
AttributeFilter
    ATTR_NAME = rekkefolge
    ATTR_VALUES = <Empty>,<Missing>,<Null>,<Unfiltered>,1
    <EMPTY> -> SQLExecutor_2 [INITIATOR]
    1 -> SQLExecutor_2 [INITIATOR]
Note: Get id for pk
SQLExecutor_2
    DATASET = $(config_db)
    POSTGRES_USER_NAME = $(config_user)
    EXPOSED_ATTRIBUTE_LIST = id
    POSTGRES_PORT = $(config_port)
    POSTGRES_HOST = $(config_host)
    COMBINE_ATTRS = Keep Initiator Attributes if Conflict
    POSTGRES_SCHEMAS_FOR_TABLE_LISTING = data
    FORMAT = POSTGRES
    POSTGRES_PASSWORD = $(config_pass)
    COMBINE_GEOM = Initiator Geometry Only
    SQL_STATEMENT = SELECT nextval('data.geometry_id_seq') as id
    POSTGRES_QUERY_FEATURE_TYPES_FOR_MERGE_FILTERS = Yes
    RESULT -> SQLExecutor [INITIATOR]
    RESULT -> AttributeRenamer_4
Note: Get dataset id
SQLExecutor
    DATASET = bigbadabom
    POSTGRES_USER_NAME = postgres
    EXPOSED_ATTRIBUTE_LIST = dataset_id
    POSTGRES_PORT = 5432
    POSTGRES_HOST = localhost
    COMBINE_ATTRS = Keep Initiator Attributes if Conflict
    POSTGRES_SCHEMAS_FOR_TABLE_LISTING = data
    FORMAT = POSTGRES
    POSTGRES_PASSWORD =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
    COMBINE_GEOM = Initiator Geometry Only
    SQL_STATEMENT = select id as dataset_id from data.dataset where description='$(Dataset)';
    POSTGRES_QUERY_FEATURE_TYPES_FOR_MERGE_FILTERS = Yes
    RESULT -> geometry (writer POSTGIS_1)
geometry (writer POSTGIS_1)
    attributes: dataset_id int8, id int8
AttributeRenamer_4
    ATTR_TABLE:
      RENAME_SET_DEFAULT id > geometry_id
      RENAME_SET_DEFAULT navn > title
    -> FeatureHolder
FeatureHolder
    -> PythonCaller
Note: Fix single quotes before inserting
PythonCaller
    PYTHONSYMBOL = FeatureProcessor
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              title = feature.getAttribute('title')
              title = title.replace("'","''")
              feature.setAttribute('title', title)
              self.pyoutput(feature)
          def close(self):
              pass
    -> SQLExecutor_3 [INITIATOR]
Note: Insert codes
SQLExecutor_3
    DATASET = $(config_db)
    POSTGRES_USER_NAME = $(config_user)
    POSTGRES_PORT = $(config_port)
    POSTGRES_HOST = $(config_host)
    COMBINE_ATTRS = Keep Result Attributes if Conflict
    POSTGRES_SCHEMAS_FOR_TABLE_LISTING = data
    FORMAT = POSTGRES
    POSTGRES_PASSWORD = $(config_pass)
    COMBINE_GEOM = Initiator Geometry Only
    SQL_STATEMENT = INSERT INTO data.codes (code, title) select '@Value(code)', '@Value(title)' WHERE NOT EXISTS (SELECT 1 FROM data.codes WHERE code = '@Value(code)');
    POSTGRES_QUERY_FEATURE_TYPES_FOR_MERGE_FILTERS = Yes
    INITIATOR -> SQLExecutor_5 [INITIATOR]
Note: Get code-id
SQLExecutor_5
    DATASET = $(config_db)
    POSTGRES_USER_NAME = $(config_user)
    EXPOSED_ATTRIBUTE_LIST = codes_id
    POSTGRES_PORT = $(config_port)
    POSTGRES_HOST = $(config_host)
    COMBINE_ATTRS = Keep Result Attributes if Conflict
    POSTGRES_SCHEMAS_FOR_TABLE_LISTING = data
    FORMAT = POSTGRES
    POSTGRES_PASSWORD = $(config_pass)
    COMBINE_GEOM = Initiator Geometry Only
    SQL_STATEMENT = select id as codes_id from data.codes where code = '@Value(code)';
    POSTGRES_QUERY_FEATURE_TYPES_FOR_MERGE_FILTERS = Yes
    RESULT -> codes_geometry (writer POSTGIS_1)
codes_geometry (writer POSTGIS_1)
    attributes: codes_id text, geometry_id text
