FME workspace 08_nibio.fmw

Parameters:
- SourceDataset_WFS = http://wfs.nibio.no/cgi-bin/ar50?SERVICE=WFS&request=GetCapabilities&VERSION=2.0.0   # Source WFS (Web Feature Service) URL
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_port:   # Python Script
      import fme
      import json
      
      data = json.load(open('../../config/postgis.json'))
      
      return data['port']
- config_host:   # Python Script
      import fme
      import json
      
      data = json.load(open('../../config/postgis.json'))
      
      return data['host']
- Dataset = ar50
- Prefix = NA
- PrefixDesc = Natursystem

Readers:
- WFS_1: WFS from $(SourceDataset_WFS)

Writers:
- POSTGIS_1: POSTGIS to $(config_db)

AR50 (reader WFS_1)
    attributes: gml_parent_id xml_buffer, gml_parent_property xml_buffer, gml_id xml_buffer, msGeometry xml_geometry, lokalid xml_buffer, objtype xml_buffer, arealtype xml_buffer, skogbonitet xml_buffer, treslag xml_buffer, jordbruk xml_buffer, dyrkbarjord xml_buffer, vegetasjonsdekke xml_buffer, kartstandard xml_buffer, informasjon xml_buffer, identifikasjon xml_buffer, navnerom xml_buffer, kopidata xml_buffer, områdeid xml_buffer, originaldatavert xml_buffer, kopidato xml_buffer, kvalitet xml_buffer, målemetode xml_buffer, oppdateringsdato xml_buffer, komid xml_buffer
    -> AttributeCreator
AttributeCreator
    ATTR_TABLE:
      SET_TO code = $(Prefix)-I1
      SET_TO created = @ReplaceRegEx(@Value(oppdateringsdato),"([ ].*)$","")
    -> AttributeKeeper
AttributeKeeper
    KEEP_ATTRS = created,code
    -> Sampler
Sampler
    RATE = 1
    SAMPLE_MODE = No
    SAMPLE_TYPE_LONG = First N Features
    SAMPLED -> SQLExecutor_4 [INITIATOR]
    NOT_SAMPLED -> Reprojector
Note: Insert dataset / (prefix should already be there from NiN-import)
SQLExecutor_4
    COMBINE_ATTRS = Keep Initiator Attributes if Conflict
    COMBINE_GEOM = Initiator Geometry Only
    DATASET = $(config_db)
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_READ_TIME_WITH_TIMEZONE = Yes
    POSTGRES_SCHEMAS_FOR_TABLE_LISTING = data
    POSTGRES_USER_NAME = $(config_user)
    SQL_STATEMENT:
      DELETE FROM data.dataset WHERE description='$(Dataset)';
      INSERT INTO data.prefix (value, description) values ('$(Prefix)', '$(PrefixDesc)') ON CONFLICT DO NOTHING;
      COMMIT;
      INSERT INTO data.dataset (prefix_id, description) Select id, '$(Dataset)' from data.prefix where value = '$(Prefix)';
    INITIATOR -> Reprojector
Reprojector
    DEST = EPSG:4326
    INTERPOLATION_TYPE_NAME = Nearest Neighbor
    RASTER_CELL_SIZE = Preserve Cells
    RASTER_TOLERANCE = 0.0
    SOURCE = Read from feature
    REPROJECTED -> SQLExecutor_2 [INITIATOR]
Note: Get id for pk
SQLExecutor_2
    COMBINE_ATTRS = Keep Initiator Attributes if Conflict
    COMBINE_GEOM = Initiator Geometry Only
    DATASET = $(config_db)
    EXPOSED_ATTRIBUTE_LIST = id
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_SCHEMAS_FOR_TABLE_LISTING = data
    POSTGRES_USER_NAME = $(config_user)
    SQL_STATEMENT = SELECT nextval('data.geometry_id_seq') as id
    RESULT -> SQLExecutor [INITIATOR]
    RESULT -> AttributeRenamer_4
Note: Get dataset id
SQLExecutor
    COMBINE_ATTRS = Keep Initiator Attributes if Conflict
    COMBINE_GEOM = Initiator Geometry Only
    DATASET = bigbadabom
    EXPOSED_ATTRIBUTE_LIST = dataset_id
    FORMAT = POSTGRES
    POSTGRES_HOST = localhost
    POSTGRES_PASSWORD =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
    POSTGRES_PORT = 5432
    POSTGRES_QUERY_FEATURE_TYPES_FOR_MERGE_FILTERS = Yes
    POSTGRES_SCHEMAS_FOR_TABLE_LISTING = data
    POSTGRES_USER_NAME = postgres
    SQL_STATEMENT = select id as dataset_id from data.dataset where description='$(Dataset)';
    RESULT -> geometry (writer POSTGIS_1)
geometry (writer POSTGIS_1)
    attributes: dataset_id int8, id int8
AttributeRenamer_4
    ATTR_TABLE = RENAME_SET_DEFAULT id > geometry_id
    -> FeatureHolder
FeatureHolder
    -> SQLExecutor_5 [INITIATOR]
Note: Get code-id
SQLExecutor_5
    COMBINE_ATTRS = Keep Result Attributes if Conflict
    COMBINE_GEOM = Initiator Geometry Only
    DATASET = $(config_db)
    EXPOSED_ATTRIBUTE_LIST = codes_id
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_SCHEMAS_FOR_TABLE_LISTING = data
    POSTGRES_USER_NAME = $(config_user)
    SQL_STATEMENT = select id as codes_id from data.codes where code = '@Value(code)';
    RESULT -> codes_geometry (writer POSTGIS_1)
codes_geometry (writer POSTGIS_1)
    attributes: codes_id text, geometry_id text, code text, created timestamp
