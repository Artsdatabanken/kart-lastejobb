FME workspace 01_updateCodes.fmw

Parameters:
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_port:   # Python Script
      import fme
      import json
      
      data = json.load(open('../../config/postgis.json'))
      
      return data['port']
- config_host:   # Python Script
      import fme
      import json
      
      data = json.load(open('../../config/postgis.json'))
      
      return data['host']

Creator
    NUM = 1
    GEOMTYPE = Geometry Object
    CREATED -> SQLExecutor_4 [INITIATOR]
SQLExecutor_4
    DATASET = $(config_db)
    POSTGRES_PASSWORD = $(config_pass)
    COMBINE_GEOM = Initiator Geometry Only
    COMBINE_ATTRS = Keep Initiator Attributes if Conflict
    FORMAT = POSTGRES
    POSTGRES_QUERY_FEATURE_TYPES_FOR_MERGE_FILTERS = Yes
    POSTGRES_PORT = $(config_port)
    POSTGRES_HOST = $(config_host)
    SQL_STATEMENT:
      update data.codes_geometry c_g
      set codes_id = c.id
      FROM data.codes c
      where c.code = c_g.code
    POSTGRES_SCHEMAS_FOR_TABLE_LISTING = data
    POSTGRES_USER_NAME = $(config_user)
