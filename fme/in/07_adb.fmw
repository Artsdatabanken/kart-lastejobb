FME workspace 07_adb.fmw

Parameters:
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_port:   # Python Script
      import fme
      import json
      
      data = json.load(open('../../config/postgis.json'))
      
      return data['port']
- config_host:   # Python Script
      import fme
      import json
      
      data = json.load(open('../../config/postgis.json'))
      
      return data['host']
- Dataset = adb
- Prefix = AR
- PrefixDesc = Art
- config_mssql_pass:   # Python Script
      import fme
      import json
      
      data = json.load(open('../../config/mssql_artsobs.json'))
      
      return data['pass']
- config_mssql_user:   # Python Script
      import fme
      import json
      
      data = json.load(open('../../config/mssql_artsobs.json'))
      
      return data['user']
- config_mssql_db:   # Python Script
      import fme
      import json
      
      data = json.load(open('../../config/mssql_artsobs.json'))
      
      return data['db']
- config_mssql_host:   # Python Script
      import fme
      import json
      
      data = json.load(open('../../config/mssql_artsobs.json'))
      
      return data['host']

Writers:
- POSTGIS_1: POSTGIS to $(config_db)
- POSTGIS_2: POSTGIS to $(config_db)

Creator
    GEOMTYPE = Geometry Object
    NUM = 1
    CREATED -> SQLExecutor_2 [INITIATOR]
    CREATED -> FeatureReader [INITIATOR]
    CREATED -> FeatureReader_2 [INITIATOR]
FeatureReader
    ATTRS_TO_EXPOSE = Id
    ATTR_ACCUM_MODE = Only Use Result
    COMBINE_GEOM = Use Result
    DATASET = $(config_mssql_db)
    FEATURETYPES = dbo.Location
    FORMAT = MSSQL_SPATIAL
    INTERACT = <No Spatial Filter>
    MSSQL_SPATIAL_COMMAND_TIMEOUT = 30
    MSSQL_SPATIAL_ENCRYPT_CONNECTION = NO
    MSSQL_SPATIAL_HANDLE_MULTIPLE_SPATIAL_COLUMNS = NO
    MSSQL_SPATIAL_PASSWORD = $(config_mssql_pass)
    MSSQL_SPATIAL_PERSISTENT_CONNECTION = NO
    MSSQL_SPATIAL_QUERY_FEATURE_TYPES_FOR_MERGE_FILTERS = Yes
    MSSQL_SPATIAL_READ_CACHE_SIZE = 10
    MSSQL_SPATIAL_SERVER = $(config_mssql_host)
    MSSQL_SPATIAL_USER_NAME = $(config_mssql_user)
    MSSQL_SPATIAL_USE_MAKE_VALID = NO
    MSSQL_SPATIAL_USE_SEARCH_ENVELOPE = NO
    MSSQL_SPATIAL_USE_SSPI = NO
    OUTPUT_FEATURES_DISPLAY = Schema and Data Features
    <OTHER> -> Sampler
Sampler
    RATE = 1
    SAMPLE_MODE = No
    SAMPLE_TYPE_LONG = First N Features
    SAMPLED -> SQLExecutor_4 [INITIATOR]
    NOT_SAMPLED -> SQLExecutor_6 [INITIATOR]
FeatureMerger_2_UnmergedRequestor: Logger
    LOG_FEATURE = LOG_ONLY
    MAXCOORDS = 20
    MAXFEATS = 20
    MESSAGE = Feature is:
    SEVERITY = INFO

Bookmark: Add prefix and dataset to database
Note: Insert prefix and dataset
SQLExecutor_4
    COMBINE_ATTRS = Keep Initiator Attributes if Conflict
    COMBINE_GEOM = Initiator Geometry Only
    DATASET = $(config_db)
    EXPOSED_ATTRIBUTE_LIST = dataset_id
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_READ_TIME_WITH_TIMEZONE = Yes
    POSTGRES_SCHEMAS_FOR_TABLE_LISTING = data
    POSTGRES_USER_NAME = $(config_user)
    SQL_STATEMENT:
      DELETE FROM data.dataset WHERE description='$(Dataset)';
      INSERT INTO data.prefix (value, description) values ('$(Prefix)', '$(PrefixDesc)') ON CONFLICT DO NOTHING;
      INSERT INTO data.dataset (prefix_id, description) Select id, '$(Dataset)' from data.prefix where value = '$(Prefix)';
      select id as dataset_id from data.dataset where description='$(Dataset)';
    RESULT -> PythonCaller_2
Note: Write global dataset_id
PythonCaller_2
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              global dataset_id
              dataset_id = feature.getAttribute("dataset_id")
              self.pyoutput(feature)
          def close(self):
              pass
    PYTHONSYMBOL = FeatureProcessor
    -> SQLExecutor_6 [INITIATOR]

Bookmark: Merge observations and locations
Note: Get id for pk
SQLExecutor_6
    COMBINE_ATTRS = Keep Result Attributes if Conflict
    COMBINE_GEOM = Initiator Geometry Only
    DATASET = $(config_db)
    EXPOSED_ATTRIBUTE_LIST = geometry_id
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_READ_TIME_WITH_TIMEZONE = Yes
    POSTGRES_SCHEMAS_FOR_TABLE_LISTING = data
    POSTGRES_USER_NAME = $(config_user)
    SQL_STATEMENT = SELECT nextval('data.geometry_id_seq') as geometry_id
    RESULT -> PythonCaller
    RESULT -> FeatureMerger [REQUESTOR]
SQLExecutor_2
    COMBINE_ATTRS = Keep Result Attributes if Conflict
    COMBINE_GEOM = Initiator Geometry Only
    DATASET = $(config_mssql_db)
    EXPOSED_ATTRIBUTE_LIST = TagId,MatchedScientificNameId,ValidScientificName,LocationId
    FORMAT = MSSQL_ADO
    MSSQL_ADO_COMMAND_TIMEOUT = 3000
    MSSQL_ADO_ENCRYPT_CONNECTION = NO
    MSSQL_ADO_MULTI_SUBNET_FAILOVER = NO
    MSSQL_ADO_PASSWORD = $(config_mssql_pass)
    MSSQL_ADO_QUERY_FEATURE_TYPES_FOR_MERGE_FILTERS = Yes
    MSSQL_ADO_SERVER = $(config_mssql_host)
    MSSQL_ADO_USER_NAME = $(config_mssql_user)
    MSSQL_ADO_USE_SSPI = NO
    SQL_STATEMENT:
      select
      distinct
      --top 1000000

      * from (
      SELECT distinct
      o.MatchedScientificNameId,
      t.ValidScientificName,
      o.LocationId,
      null as TagId
      from
      dbo.Observation o,
      dbo.Taxon t
      where
      t.ValidScientificNameId = o.MatchedScientificNameId

      union all

      SELECT
      distinct
      o.MatchedScientificNameId,
      t.ValidScientificName,
      o.LocationId,
      ot.TagId
      from
      dbo.Observation o,
      dbo.Taxon t,
      dbo.ObservationTags ot
      where
      t.ValidScientificNameId = o.MatchedScientificNameId and
      ot.ObservationId = o.id
      ) as t
    RESULT -> FeatureMerger [SUPPLIER]
FeatureMerger
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(Id) @Value(LocationId) AUTO
    MERGE_TYPE = Attributes Only
    PROCESS_DUPS = YES
    REJECT_NULL_MISSING_KEYS = No
    SUPPLIERS_FIRST = No
    MERGED -> AttributeFilter
    UNMERGED_REQUESTOR -> FeatureMerger_UnmergedRequestor_2
    UNUSED_SUPPLIER -> FeatureMerger_UnusedSupplier_2
AttributeFilter
    ATTR_NAME = TagId
    ATTR_VALUES = <Empty>,<Missing>,<Null>,<Unfiltered>,3,4
    <EMPTY> -> AttributeCreator
    <MISSING> -> AttributeCreator
    <NULL> -> AttributeCreator
    3 -> AttributeCreator
    4 -> AttributeCreator
FeatureMerger_UnmergedRequestor_2: Logger
    LOG_FEATURE = LOG_ONLY
    MAXCOORDS = 20
    MAXFEATS = 20
    MESSAGE = Feature is:
    SEVERITY = INFO
FeatureMerger_UnusedSupplier_2: Logger
    LOG_FEATURE = LOG_ONLY
    MAXCOORDS = 20
    MAXFEATS = 20
    MESSAGE = Feature is:
    SEVERITY = INFO

Bookmark: Write geometry
Note: Read global dataset_id
PythonCaller
    NEW_ATTRIBUTES = dataset_id
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              feature.setAttribute("dataset_id", dataset_id)
              self.pyoutput(feature)
          def close(self):
              pass
    PYTHONSYMBOL = FeatureProcessor
    -> Reprojector
Reprojector
    DEST = EPSG:4326
    INTERPOLATION_TYPE_NAME = Nearest Neighbor
    RASTER_CELL_SIZE = Preserve Cells
    RASTER_TOLERANCE = 0.0
    SOURCE = Read from feature
    REPROJECTED -> AttributeRenamer_2
AttributeRenamer_2
    ATTR_TABLE = RENAME_SET_DEFAULT geometry_id > id
    -> geometry (writer POSTGIS_1)
geometry (writer POSTGIS_1)
    attributes: dataset_id int8, id int8

Bookmark: Merge in code
AttributeCreator
    ATTR_TABLE = SET_TO code = $(Prefix)-@Value(MatchedScientificNameId)
    -> AttributeRenamer_4
AttributeRenamer_4
    ATTR_TABLE:
      RENAME_SET_DEFAULT id_location > geometry_id
      RENAME_SET_DEFAULT ValidScientificName > title
    -> FeatureMerger_2 [REQUESTOR]
FeatureReader_2
    ATTRS_TO_EXPOSE = code id
    ATTR_ACCUM_MODE = Only Use Result
    COMBINE_GEOM = Use Result
    DATASET = $(config_db)
    FEATURETYPES = data.codes
    FORMAT = POSTGRES
    OUTPUT_FEATURES_DISPLAY = Schema and Data Features
    POSTGRES_FEATURES_PER_FETCH = 10000
    POSTGRES_HOST = $(config_host)
    POSTGRES_PASSWORD = $(config_pass)
    POSTGRES_PORT = $(config_port)
    POSTGRES_QUERY_FEATURE_TYPES_FOR_MERGE_FILTERS = Yes
    POSTGRES_READ_TIME_WITH_TIMEZONE = Yes
    POSTGRES_USER_NAME = $(config_user)
    WHERE = code like 'AR%'
    <OTHER> -> FeatureMerger_2 [SUPPLIER]
FeatureMerger_2
    ATTR_ACCUM_MODE = Merge Supplier
    ATTR_CONFLICT_RES = Use Requestor
    IGNORE_NULLS = No
    JOIN_KEYS = @Value(code) @Value(code) AUTO
    MERGE_TYPE = Attributes Only
    PROCESS_DUPS = NO
    REJECT_NULL_MISSING_KEYS = No
    SUPPLIERS_FIRST = No
    MERGED -> AttributeRenamer_3
    UNMERGED_REQUESTOR -> FeatureMerger_2_UnmergedRequestor

Bookmark: Write code
AttributeRenamer_3
    ATTR_TABLE = RENAME_SET_DEFAULT id > codes_id
    -> DuplicateFilter
DuplicateFilter
    INPUT_ORDERED_CHOICE = No
    KEYATTR = code codes_id
    UNIQUE -> codes_geometry (writer POSTGIS_2)
codes_geometry (writer POSTGIS_2)
    attributes: codes_id text, geometry_id text, code text
