FME workspace 06_nin.fmw
History: 2017-06-16,KJEPET,Påbegynt endring til nin_hovedbase og norsk datamodell

Parameters:
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_port:   # Python Script
      import fme
      import json
      
      data = json.load(open('../../config/postgis.json'))
      
      return data['port']
- config_host:   # Python Script
      import fme
      import json
      
      data = json.load(open('../../config/postgis.json'))
      
      return data['host']
- Dataset = nin
- Prefix = NA
- PrefixDesc = Natursystem
- config_mssql_pass:   # Python Script
      import fme
      import json
      
      data = json.load(open('../../config/mssql.json'))
      
      return data['pass']
- config_mssql_user:   # Python Script
      import fme
      import json
      
      data = json.load(open('../../config/mssql.json'))
      
      return data['user']
- config_mssql_db:   # Python Script
      import fme
      import json
      
      data = json.load(open('../../config/mssql.json'))
      
      return data['db']
- config_mssql_host:   # Python Script
      import fme
      import json
      
      data = json.load(open('../../config/mssql.json'))
      
      return data['host']

Writers:
- POSTGIS_1: POSTGIS to $(config_db)
- POSTGIS_2: POSTGIS to $(config_db)

Creator
    GEOMTYPE = Geometry Object
    NUM = 1
    CREATED -> FeatureReader [INITIATOR]
FeatureReader
    ATTR_ACCUM_MODE = Only Use Result
    COMBINE_GEOM = Use Result
    DATASET = $(config_mssql_db)
    FEATURETYPES = nin_eier.NATUROMRAADE
    FORMAT = MSSQL_SPATIAL
    INTERACT = <No Spatial Filter>
    MSSQL_SPATIAL_COMMAND_TIMEOUT = 30
    MSSQL_SPATIAL_ENCRYPT_CONNECTION = NO
    MSSQL_SPATIAL_HANDLE_MULTIPLE_SPATIAL_COLUMNS = NO
    MSSQL_SPATIAL_PASSWORD = $(config_mssql_pass)
    MSSQL_SPATIAL_PERSISTENT_CONNECTION = NO
    MSSQL_SPATIAL_QUERY_FEATURE_TYPES_FOR_MERGE_FILTERS = Yes
    MSSQL_SPATIAL_READ_CACHE_SIZE = 10
    MSSQL_SPATIAL_SERVER = $(config_mssql_host)
    MSSQL_SPATIAL_USER_NAME = $(config_mssql_user)
    MSSQL_SPATIAL_USE_MAKE_VALID = NO
    MSSQL_SPATIAL_USE_SEARCH_ENVELOPE = NO
    MSSQL_SPATIAL_USE_SSPI = NO
    OUTPUT_FEATURES_DISPLAY = Schema and Data Features
    WHERE = nivaa in ('NS','NA')
    <OTHER> -> AttributeRenamer_Naturomraade
    INITIATOR -> SQLExecutor_NaturomradeType [INITIATOR]
Note: Fra nin_hovedbase_sde: / Hent Naturområtetyper der NaturomraadeFKID matcher lokalId fra Naturomraade / Filtrer vekk: / Bruker = Mijødir eller Geodat / KODE = NULL
SQLExecutor_NaturomradeType
    COMBINE_ATTRS = Result Attributes Only
    COMBINE_GEOM = Initiator Geometry Only
    DATASET = $(config_mssql_db)
    EXPOSED_ATTRIBUTE_LIST = andel,beskrivelse,brukernavn,kartlagtDato,kode,kodeFoersteVersjon,kodeVersjon,NaturomraadetypeLokalID,NaturomraadeFKID,ninKartleggingsenhet,ninHovedgruppe,ninHovedtype,omraadetypeId
    FORMAT = MSSQL_ADO
    MSSQL_ADO_COMMAND_TIMEOUT = 30
    MSSQL_ADO_ENCRYPT_CONNECTION = NO
    MSSQL_ADO_PASSWORD = $(config_mssql_pass)
    MSSQL_ADO_QUERY_FEATURE_TYPES_FOR_MERGE_FILTERS = Yes
    MSSQL_ADO_SERVER = $(config_mssql_host)
    MSSQL_ADO_USER_NAME = $(config_mssql_user)
    MSSQL_ADO_USE_SSPI = NO
    SQL_STATEMENT:
      SELECT [andel]
      ,[beskrivelse]
      ,[brukernavn]
      ,[kartlagtDato]
      ,[kode]
      ,[kodeFoersteVersjon]
      ,[kodeVersjon]
      ,[lokalId] AS NaturomraadetypeLokalID
      ,[NaturomraadeFKID]
      ,[ninHovedgruppe]
      ,[ninHovedtype]
      ,[ninKartleggingsenhet]
      ,[omraadetypeId]
      FROM [Nin_Hovedbase_SDE].[nin_eier].[NATUROMRAADETYPE]
      WHERE
          (brukernavn NOT IN (SELECT brukernavn FROM nin_eier.BRUKER WHERE firmaNavn IN ('Miljødirektoratet', 'Geodata')) OR brukernavn is null)
          --AND ([NaturomraadeFKID] = '@Value(localid)')
    RESULT -> FeatureMerger_NaturomradeType [REQUESTOR]
    INITIATOR -> SQLExecutor_5 [INITIATOR]
FeatureMerger_NaturomradeType
    ATTR_ACCUM_MODE = Merge Supplier
    ATTR_CONFLICT_RES = Use Requestor
    IGNORE_NULLS = No
    JOIN_KEYS = @Value(NaturomraadeFKID) @Value(localid) AUTO
    MERGE_TYPE = Attributes Only
    PROCESS_DUPS = No
    REJECT_NULL_MISSING_KEYS = No
    SUPPLIERS_FIRST = No
    MERGED -> TestFilter_kode
TestFilter_kode
    DEFAULT_VALUE = <UNFILTERED>
    TEST_LIST:
      BOOL_OP,OR,COMPOSITE_TEST,<Unused>,TEST_CLAUSE,"TEST kode ATTRIBUTE_VALUE_NULL """"
      TEST kode ATTRIBUTE_IS_EMPTY """"
      TEST kode ATTRIBUTE_IS_MISSING """"",kode er blank
    kode er blank -> TestFilter_kode_2
    <UNFILTERED> -> AttributeFilter_andel
Note: kan kode genereres?
TestFilter_kode_2
    DEFAULT_VALUE = <UNFILTERED>
    TEST_LIST:
      BOOL_OP,AND,COMPOSITE_TEST,<Unused>,TEST_CLAUSE,"TEST @Value(ninHovedgruppe) ATTRIBUTE_HAS_VALUE """"
      TEST @Value(ninHovedtype) ATTRIBUTE_HAS_VALUE """"
      TEST @Value(ninKartleggingsenhet) ATTRIBUTE_HAS_VALUE """"",hovedgr-hovedtype-kartlehet finnes
    hovedgr-hovedtype-kartlehet finnes -> AttributeCreator_kode_3
Note: Lag kode
AttributeCreator_kode_3
    ATTR_TABLE = SET_TO kode = NA-@Value(ninHovedgruppe)@Value(ninHovedtype)-@Value(ninKartleggingsenhet)
    -> AttributeFilter_andel
Note: Andel = NULL?
AttributeFilter_andel
    ATTR_NAME = andel
    ATTR_VALUES = <EMPTY>,<MISSING>,<NULL>,<UNFILTERED>
    <NULL> -> TestFilter_Kode
    <UNFILTERED> -> AttributeRenamer_NatureAreaType
Note: Andel mangler / NA L og NA M aksepteres / Ikke mosaikk = 1 aksapteres
TestFilter_Kode
    DEFAULT_VALUE = <UNFILTERED>
    TEST_LIST:
      BOOL_OP,OR,COMPOSITE_TEST,<Unused>,TEST_CLAUSE,"TEST @Value(kode) BEGINS_WITH NA L
      TEST @Value(kode) BEGINS_WITH NA M",NA_L_og_M,BOOL_OP,OR,COMPOSITE_TEST,<Unused>,TEST_CLAUSE,"TEST @Value(mosaikk) = 0",Ikke Mosaikk (0)
    NA_L_og_M -> AttributeCreator_andel_sq_2
    Ikke Mosaikk (0) -> AttributeCreator_andel_sq_2
    <UNFILTERED> -> TestFilter_Kode__Unfiltered_
TestFilter_Kode__Unfiltered_: Logger
    MAXCOORDS = 20
    MAXFEATS = 20
    MESSAGE = Feature is:
Note: Sett aksepterte Andel til 10 / (pga NOT NULL for felt) / FEIL I DATAMODELL?
AttributeCreator_andel_sq_2
    ATTR_TABLE = SET_TO andel = 10
    -> AttributeRenamer_NatureAreaType
AttributeRenamer_NatureAreaType
    ATTR_TABLE = RENAME_SET_DEFAULT omraadetypeId > tematiskId
    -> Tester_noeyaktighet
Tester_noeyaktighet
    BOOL_OP = OR
    TEST_CLAUSE = TEST @Value(noeyaktighet) ATTRIBUTE_HAS_VALUE ""
    PASSED -> attributeRenamer_naturområdetype
    FAILED -> AttributeCreator_3
AttributeCreator_3
    ATTR_TABLE = SET_TO noeyaktighet = 0
    -> attributeRenamer_naturområdetype
Note: attributeRenamer_naturområdetype / Bruker naturomraade.noeyaktighet som verdi / på totalklassifikasjonskvalitet / Mangler verdi = 0
attributeRenamer_naturområdetype: AttributeRenamer
    ATTR_TABLE:
      RENAME_SET_DEFAULT NaturomraadetypeLokalID > localId
      RENAME_SET_DEFAULT noeyaktighet > totalklassifikasjonskvalitet
    -> DateFormatter
DateFormatter
    DATE_ATTR = kartlagtDato
    FMT = FME Date/Time (%Y%m%d%H%M%S)
    INVALID_DATE_VALUE = _FME_NO_OP_
    SRCFMT = Unknown - Automatic Detection
    -> AttributeTrimmer
AttributeTrimmer
    SRC_ATTRS = kode
    TRIM_CHARS = " "
    TRIM_TO_NONE = Yes
    TRIM_TYPE = Right
    -> StringReplacer
StringReplacer
    CASE = NO
    FIND_TEXT = " "
    NO_MATCH = _FME_NO_OP_
    REGEXP = NO
    REPLACE_TEXT = -
    SRC_ATTRS = kode
    -> AttributeRenamer_7
AttributeRenamer_7
    ATTR_TABLE = RENAME_SET_DEFAULT kode > code
    -> AttributeKeeper
AttributeKeeper
    KEEP_ATTRS = code,localId,kartlagtDato,geometry_id,andel
    -> AttributeRenamer_Beskrivelsesvariabel
AttributeRenamer_Beskrivelsesvariabel
    ATTR_TABLE:
      RENAME_SET_DEFAULT lokalId > beskrivelseLokalId
      RENAME_SET_DEFAULT variabelTrinn > trinn
      RENAME_SET_DEFAULT andel > fraction
    -> StringReplacer_2
    -> FeatureMerger [SUPPLIER]
StringReplacer_2
    CASE = NO
    FIND_TEXT = _
    NO_MATCH = _FME_NO_OP_
    REGEXP = NO
    REPLACE_TEXT = -
    SRC_ATTRS = code
    -> FeatureMerger_2 [REQUESTOR]
SQLExecutor_5
    COMBINE_ATTRS = Keep Initiator Attributes if Conflict
    COMBINE_GEOM = Initiator Geometry Only
    DATASET = $(config_mssql_db)
    EXPOSED_ATTRIBUTE_LIST = beskrivelse,beskrivelseId,brukernavn,kartlagtDato,kode,kodeFoersteVersjon,kodeVersjon,lokalId,omraadetypeFKID,omraadetypeId,variabelGruppe,variabelNavn,variabelTema,variabelTrinn,verdi
    FORMAT = MSSQL_ADO
    MSSQL_ADO_COMMAND_TIMEOUT = 30
    MSSQL_ADO_ENCRYPT_CONNECTION = NO
    MSSQL_ADO_PASSWORD = $(config_mssql_pass)
    MSSQL_ADO_QUERY_FEATURE_TYPES_FOR_MERGE_FILTERS = Yes
    MSSQL_ADO_SERVER = $(config_mssql_host)
    MSSQL_ADO_USER_NAME = $(config_mssql_user)
    MSSQL_ADO_USE_SSPI = NO
    SQL_STATEMENT:
      SELECT
            [beskrivelseId]
            ,[brukernavn]
            ,[kartlagtDato]
            ,[kode]
            ,[kodeFoersteVersjon]
            ,[kodeVersjon]
            ,[verdi]
            ,[variabelGruppe]
            ,[variabelTema]
            ,[variabelNavn]
            ,[variabelTrinn]
            ,[lokalId]
            ,[omraadetypeId]
            ,[omraadetypeFKID]
            ,[beskrivelse]
        FROM [Nin_Hovedbase_SDE].[nin_eier].[BESKRIVELSESVARIABEL]
        WHERE
              (
              [brukernavn] NOT IN
                  (SELECT [brukernavn] FROM [nin_hovedbase_SDE].[nin_eier].[BRUKER] WHERE [firmaNavn] IN ('Miljødirektoratet', 'Geodata'))
              OR
              brukernavn is null
              )
      --AND omraadetypeFKID = '@Value(localId)'
      AND
          kode not like '%-x'
      AND
          kode not like '%-XY'
    RESULT -> FeatureMerger [REQUESTOR]
    INITIATOR -> SQLExecutor_3 [INITIATOR]
StringReplacer_3
    CASE = NO
    FIND_TEXT = _
    NO_MATCH = _FME_NO_OP_
    REGEXP = NO
    REPLACE_TEXT = -
    SRC_ATTRS = code
    -> FeatureMerger_2 [REQUESTOR]
SQLExecutor_3
    COMBINE_ATTRS = Keep Initiator Attributes if Conflict
    COMBINE_GEOM = Initiator Geometry Only
    DATASET = $(config_db)
    EXPOSED_ATTRIBUTE_LIST = codes_id,code
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_READ_TIME_WITH_TIMEZONE = Yes
    POSTGRES_SCHEMAS_FOR_TABLE_LISTING = data
    POSTGRES_USER_NAME = $(config_user)
    SQL_STATEMENT:
      select id as codes_id, code from data.codes
      where code like 'NA-%' OR code like 'NA-BS-%'
      --where code = '@Value(code)'
    RESULT -> FeatureMerger_2 [SUPPLIER]
AttributeRenamer_Beskrivelsesvariabel_Output: Inspector

Bookmark: Write geometry
Note: AttributeRenamer_Naturomraade
AttributeRenamer_Naturomraade
    ATTR_TABLE = RENAME_SET_DEFAULT lokalId > localid
    -> AttributeFilter
Note: Tom beskrivelse?
AttributeFilter
    ATTR_NAME = beskrivelse
    ATTR_VALUES = <EMPTY>,<MISSING>,<NULL>,<UNFILTERED>
    <EMPTY> -> AttributeCreator_2
    <MISSING> -> AttributeCreator_2
    <NULL> -> AttributeCreator_2
    <UNFILTERED> -> AttributeCreator
AttributeCreator_2
    ATTR_TABLE = SET_TO beskrivelse
    -> AttributeCreator
Note: naturnivå_id = 4 (Natursystem)
AttributeCreator
    ATTR_TABLE:
      SET_TO versjonId = 2.1
      SET_TO institusjon = Miljødirektoratet
      SET_TO versjon = 2.1
      SET_TO navnerom = NO.MILJODIREKTORATET.NIN
      SET_TO naturnivå_id = 4
      SET_TO stedfestingskvalitet = 0
    -> GeometryFilter
GeometryFilter
    BREAK_AGG = No
    GEOM_PORT_NAMES = Area Surface Null
    AREA -> GeometryValidator
    SURFACE -> GeometryValidator
GeometryValidator
    ANGULAR_TOLERANCE_CHOICE = Automatic
    AREA_ORIENTATION = AREA_ORIENTATION
    CHECK_AREA_CHOICE = No
    CHECK_HOLE_TOUCHING_POLYGON = No
    CONNECT_Z_MODE_SI = First Wins
    FLIP_APPEARANCES_CHOICE = Yes
    ISSUE_ATTR_NAME = _issues
    MISSING_TEXTURE_COORDINATES = MISSING_TEXTURE_COORDINATES
    NULL_REMOVAL = NULL_REMOVAL
    ORIENTATION_CHECK_DIR = Valid
    PLANAR_SURFACE = PLANAR_SURFACE
    PRESETS = Custom
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    SELF_INTERSECTING = SELF_INTERSECTING
    SHELL_VALIDATION = SHELL_VALIDATION
    SOLID_VOID_REPAIR = SOLID_VOID_REPAIR
    SUMMARY = Brief
    THICKNESS_TOLERANCE_CHOICE = Automatic
    PASSED -> AttributeRenamer_3
    REPAIRED -> AttributeRenamer_3
AttributeRenamer_3
    ATTR_TABLE = RENAME_SET_DEFAULT ninID > tematiskId
    -> Reprojector
Reprojector
    DEST = EPSG:4326
    INTERPOLATION_TYPE_NAME = Nearest Neighbor
    RASTER_CELL_SIZE = Preserve Cells
    RASTER_TOLERANCE = 0.0
    SOURCE = Read from feature
    REPROJECTED -> Sampler
Sampler
    RATE = 1
    SAMPLE_MODE = No
    SAMPLE_TYPE_LONG = First N Features
    SAMPLED -> SQLExecutor_4 [INITIATOR]
    NOT_SAMPLED -> SQLExecutor_2 [INITIATOR]
Note: Insert prefix and dataset
SQLExecutor_4
    COMBINE_ATTRS = Keep Initiator Attributes if Conflict
    COMBINE_GEOM = Initiator Geometry Only
    DATASET = $(config_db)
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_SCHEMAS_FOR_TABLE_LISTING = data
    POSTGRES_USER_NAME = $(config_user)
    SQL_STATEMENT:
      DELETE FROM data.dataset WHERE description='$(Dataset)';
      INSERT INTO data.prefix (value, description) values ('$(Prefix)', '$(PrefixDesc)') ON CONFLICT DO NOTHING;
      COMMIT;
      INSERT INTO data.dataset (prefix_id, description) Select id, '$(Dataset)' from data.prefix where value = '$(Prefix)';
    INITIATOR -> SQLExecutor_2 [INITIATOR]
Note: Get id for pk
SQLExecutor_2
    COMBINE_ATTRS = Keep Initiator Attributes if Conflict
    COMBINE_GEOM = Initiator Geometry Only
    DATASET = $(config_db)
    EXPOSED_ATTRIBUTE_LIST = id
    FORMAT = POSTGRES
    POSTGRES_HOST = $(config_host)
    POSTGRES_PASSWORD = $(config_pass)
    POSTGRES_PORT = $(config_port)
    POSTGRES_QUERY_FEATURE_TYPES_FOR_MERGE_FILTERS = Yes
    POSTGRES_SCHEMAS_FOR_TABLE_LISTING = data
    POSTGRES_USER_NAME = $(config_user)
    SQL_STATEMENT = SELECT nextval('data.geometry_id_seq') as id
    RESULT -> SQLExecutor [INITIATOR]
    RESULT -> AttributeRenamer_6
AttributeRenamer_6
    ATTR_TABLE = RENAME_SET_DEFAULT id > geometry_id
    -> FeatureHolder
FeatureHolder
    -> FeatureMerger_NaturomradeType [SUPPLIER]
    -> localid_geometry (writer POSTGIS_2)
Note: FeatureMerger_NaturomradeType
localid_geometry (writer POSTGIS_2)
    attributes: localid text, geometry_id int8
Note: Get dataset id
SQLExecutor
    COMBINE_ATTRS = Keep Initiator Attributes if Conflict
    COMBINE_GEOM = Initiator Geometry Only
    DATASET = bigbadabom
    EXPOSED_ATTRIBUTE_LIST = dataset_id
    FORMAT = POSTGRES
    POSTGRES_HOST = localhost
    POSTGRES_PASSWORD =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
    POSTGRES_PORT = 5432
    POSTGRES_QUERY_FEATURE_TYPES_FOR_MERGE_FILTERS = Yes
    POSTGRES_SCHEMAS_FOR_TABLE_LISTING = data
    POSTGRES_USER_NAME = postgres
    SQL_STATEMENT = select id as dataset_id from data.dataset where description='$(Dataset)';
    RESULT -> geometry (writer POSTGIS_1)
geometry (writer POSTGIS_1)
    attributes: dataset_id int8, id int8

Bookmark: New Bookmark
FeatureMerger
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(omraadetypeFKID) @Value(localId) AUTO
    MERGE_TYPE = Attributes Only
    PROCESS_DUPS = Yes
    REJECT_NULL_MISSING_KEYS = No
    SUPPLIERS_FIRST = No
    MERGED -> AttributeFilter_variabelGruppe
Note: AttributeFilter_uLKM
AttributeFilter_variabelGruppe
    ATTR_NAME = variabelGruppe
    ATTR_VALUES = <EMPTY>,<MISSING>,<NULL>,<UNFILTERED>,Mdir,uLKM
    <UNFILTERED> -> AttributeCreator_BeskrivelsesVar2
    Mdir -> AttributeCreator_BeskrivelsesVar2
    uLKM -> AttributeCreator_BeskrivelsesVar
AttributeCreator_BeskrivelsesVar2
    ATTR_TABLE = SET_TO BeskrivelsesVarKode = @Value(kode)
    -> AttributeFilter_verdi
AttributeCreator_BeskrivelsesVar
    ATTR_TABLE = SET_TO BeskrivelsesVarKode = @Value(variabelNavn)
    -> AttributeFilter_verdi

Bookmark: Fiks_nullverdier
  Set blank streng i stedet for nullverdi i verdi, kode og beskrivelse
AttributeFilter_verdi
    ATTR_NAME = verdi
    ATTR_VALUES = <EMPTY>,<MISSING>,<NULL>,<UNFILTERED>
    <NULL> -> AttributeCreator_verdi
    <UNFILTERED> -> AttributeFilter_kode
AttributeCreator_verdi
    ATTR_TABLE = SET_TO value
    -> AttributeFilter_kode
AttributeFilter_kode
    ATTR_NAME = kode
    ATTR_VALUES = <EMPTY>,<MISSING>,<NULL>,<UNFILTERED>
    <NULL> -> AttributeCreator_kode
    <UNFILTERED> -> AttributeFilter_beskrivelse
AttributeCreator_kode
    ATTR_TABLE = SET_TO kode
    -> AttributeFilter_beskrivelse
AttributeFilter_beskrivelse
    ATTR_NAME = beskrivelse
    ATTR_VALUES = <EMPTY>,<MISSING>,<NULL>,<UNFILTERED>
    <NULL> -> AttributeCreator_beskrivelse
    <UNFILTERED> -> AttributeRenamer_2
AttributeCreator_beskrivelse
    ATTR_TABLE = SET_TO beskrivelse
    -> AttributeRenamer_2

Bookmark: New Bookmark
AttributeRenamer_2
    ATTR_TABLE:
      RENAME_SET_DEFAULT beskrivelseId > tematiskId
      RENAME_SET_DEFAULT beskrivelseLokalId > localId
    -> AttributeFilter_VariabelGruppe
Note: Beskrivelsesvariabel er av / variabelGruppe mDir?
AttributeFilter_VariabelGruppe
    ATTR_NAME = variabelGruppe
    ATTR_VALUES = <EMPTY>,<MISSING>,<NULL>,<UNFILTERED>,Mdir
    <UNFILTERED> -> DateFormatter_2
DateFormatter_2
    DATE_ATTR = kartlagt
    FMT = FME Date/Time (%Y%m%d%H%M%S)
    INVALID_DATE_VALUE = _FME_NO_OP_
    SRCFMT = Unknown - Automatic Detection
    -> AttributeRemover
AttributeRemover
    REMOVE_ATTRS = code,fraction
    -> StringConcatenator
StringConcatenator
    ACTION = Create New Attribute
    PARM_LINE = @UpperCase(NA-BS-@Value(kode))
    VAL_ATTR = code
    -> StringReplacer_3

Bookmark: New Bookmark
FeatureMerger_2
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(code) @Value(code) AUTO
    MERGE_TYPE = Attributes Only
    PROCESS_DUPS = Yes
    REJECT_NULL_MISSING_KEYS = No
    SUPPLIERS_FIRST = No
    MERGED -> DuplicateFilter
DuplicateFilter
    INPUT_ORDERED_CHOICE = No
    KEYATTR = geometry_id codes_id
    UNIQUE -> AttributeRenamer
AttributeRenamer
    ATTR_TABLE = RENAME_SET_DEFAULT kartlagtDato > created
    -> codes_geometry (writer POSTGIS_2)
codes_geometry (writer POSTGIS_2)
    attributes: codes_id text, geometry_id text, code text, fraction int8, created timestamp

FME custom transformer GUIDGenerator
Creates an ESRI GUID ID by creating a UUID enclosed by curly {}.
Input Ports
    Input
Accepts all types of features
    Output Ports
    Output
Returns all features with an additional GFID attribute

INPUT (input)
    -> UUIDGENERATOR_2
Note: Create UUID
UUIDGENERATOR_2: UUIDGenerator
    UUID_ATTR = GFID
    -> CONCATENATOR_2
Note: Enclose the UUID by {}
CONCATENATOR_2: StringConcatenator
    ACTION = Create New Attribute
    PARM_LINE = {@Value(GFID)}
    VAL_ATTR = GFID
    -> OUTPUT (output)
OUTPUT (output)
