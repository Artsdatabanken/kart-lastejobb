FME workspace 09_bioTagger.fmw

Parameters:
- config_pass:   # Python Script
      import fme
      import json
      
      data = json.load(open('../../config/postgis.json'))
      
      return data['pass']
- config_user:   # Python Script
      import fme
      import json
      
      data = json.load(open('../../config/postgis.json'))
      
      return data['user']
- config_db:   # Python Script
      import fme
      import json
      
      data = json.load(open('../../config/postgis.json'))
      
      return data['db']
- config_port:   # Python Script
      import fme
      import json
      
      data = json.load(open('../../config/postgis.json'))
      
      return data['port']
- config_host:   # Python Script
      import fme
      import json
      
      data = json.load(open('../../config/postgis.json'))
      
      return data['host']

Writers:
- POSTGIS_1: POSTGIS to $(config_db)

Creator
    NUM = 1
    GEOMTYPE = Geometry Object
    CREATED -> SQLExecutor_2 [INITIATOR]
    CREATED -> SQLExecutor_3 [INITIATOR]
Note: Fetches dataset_id for NA
SQLExecutor_2
    SQL_STATEMENT:
      select
      d.id as dataset_id,
      p.value as prefix
      from
      data.dataset d,
      data.prefix p
      where
      d.prefix_id = p.id and p.value = 'NA'
    POSTGRES_PASSWORD = $(config_pass)
    POSTGRES_PORT = $(config_port)
    POSTGRES_QUERY_FEATURE_TYPES_FOR_MERGE_FILTERS = Yes
    POSTGRES_USER_NAME = $(config_user)
    DATASET = $(config_db)
    COMBINE_GEOM = Initiator Geometry Only
    FORMAT = POSTGRES
    COMBINE_ATTRS = Result Attributes Only
    EXPOSED_ATTRIBUTE_LIST = dataset_id
    POSTGRES_HOST = $(config_host)
    RESULT -> FeatureReader [INITIATOR]
FeatureReader
    POSTGIS_QUERY_FEATURE_TYPES_FOR_MERGE_FILTERS = Yes
    POSTGIS_USER_NAME = $(config_user)
    POSTGIS_USE_TRUE_POSTGIS_TYPES = yes
    FEATURETYPES = data.geometry
    POSTGIS_FEATURES_PER_FETCH = 10000
    ATTR_CONFLICT_RES = Use Result
    POSTGIS_PASSWORD = $(config_pass)
    COMBINE_GEOM = Use Result
    ATTRS_TO_EXPOSE = id
    POSTGIS_POSTGIS_EXPOSE_FORMAT_ATTRS = postgres_oid,int4
    FORMAT = POSTGIS
    OUTPUT_FEATURES_DISPLAY = Schema and Data Features
    INTERACT = <No Spatial Filter>
    ATTR_ACCUM_MODE = Merge Initiator and Result
    DATASET = $(config_db)
    POSTGIS_PORT = $(config_port)
    POSTGIS_DISABLE_COLLECTION_SPLITTING = yes
    WHERE = dataset_id = @Value(dataset_id)
    POSTGIS_USE_SEARCH_ENVELOPE = NO
    POSTGIS_HOST = $(config_host)
    <OTHER> -> SQLExecutor_5 [INITIATOR]
Note: delete existing tags
SQLExecutor_5
    SQL_STATEMENT:
      delete FROM data.codes_geometry cg
      where
      (cg.code like 'BS_6SO%' or cg.code like 'BS_6SE%')
      AND
      cg.geometry_id = @Value(id)
    POSTGRES_PASSWORD = $(config_pass)
    POSTGRES_PORT = $(config_port)
    POSTGRES_QUERY_FEATURE_TYPES_FOR_MERGE_FILTERS = Yes
    POSTGRES_USER_NAME = $(config_user)
    DATASET = $(config_db)
    COMBINE_GEOM = Initiator Geometry Only
    FORMAT = POSTGRES
    COMBINE_ATTRS = Keep Initiator Attributes if Conflict
    POSTGRES_HOST = $(config_host)
    INITIATOR -> AttributeRenamer_2
AttributeRenamer_2
    ATTR_TABLE = RENAME_SET_DEFAULT id > geometry_id
    -> Reprojector_2
Reprojector_2
    SOURCE = Read from feature
    RASTER_CELL_SIZE = Preserve Cells
    DEST = EPSG:32633
    INTERPOLATION_TYPE_NAME = Nearest Neighbor
    REPROJECTED -> SpatialRelator [Requestor]
Note: Fetches dataset_id for 6SO/6SE
SQLExecutor_3
    SQL_STATEMENT:
      select
      d.id as dataset_id,
      p.value as prefix
      from
      data.dataset d,
      data.prefix p
      where
      d.description = 'nina' and
      d.prefix_id = p.id
    POSTGRES_PASSWORD = $(config_pass)
    POSTGRES_PORT = $(config_port)
    POSTGRES_QUERY_FEATURE_TYPES_FOR_MERGE_FILTERS = Yes
    POSTGRES_USER_NAME = $(config_user)
    DATASET = $(config_db)
    COMBINE_GEOM = Initiator Geometry Only
    FORMAT = POSTGRES
    COMBINE_ATTRS = Result Attributes Only
    EXPOSED_ATTRIBUTE_LIST = dataset_id
    POSTGRES_HOST = $(config_host)
    RESULT -> FeatureReader_3 [INITIATOR]
FeatureReader_3
    POSTGIS_QUERY_FEATURE_TYPES_FOR_MERGE_FILTERS = Yes
    POSTGIS_USER_NAME = $(config_user)
    POSTGIS_USE_TRUE_POSTGIS_TYPES = yes
    FEATURETYPES = data.geometry
    POSTGIS_FEATURES_PER_FETCH = 10000
    ATTR_CONFLICT_RES = Use Result
    POSTGIS_PASSWORD = $(config_pass)
    COMBINE_GEOM = Use Result
    ATTRS_TO_EXPOSE = id
    POSTGIS_POSTGIS_EXPOSE_FORMAT_ATTRS = postgres_oid,int4
    FORMAT = POSTGIS
    OUTPUT_FEATURES_DISPLAY = Schema and Data Features
    INTERACT = <No Spatial Filter>
    ATTR_ACCUM_MODE = Merge Initiator and Result
    DATASET = $(config_db)
    POSTGIS_PORT = $(config_port)
    POSTGIS_DISABLE_COLLECTION_SPLITTING = yes
    WHERE = dataset_id = @Value(dataset_id)
    POSTGIS_USE_SEARCH_ENVELOPE = NO
    POSTGIS_HOST = $(config_host)
    <OTHER> -> SQLExecutor_4 [INITIATOR]
Note: Joins in codes
SQLExecutor_4
    SQL_STATEMENT:
      select
      c.code as code
      ,c.id as codes_id
      from
      data.codes c,
      data.codes_geometry cg
      where
      c.id = cg.codes_id
      and
      cg.geometry_id = @Value(id)
    POSTGRES_PASSWORD = $(config_pass)
    POSTGRES_PORT = $(config_port)
    POSTGRES_QUERY_FEATURE_TYPES_FOR_MERGE_FILTERS = Yes
    POSTGRES_USER_NAME = $(config_user)
    DATASET = $(config_db)
    COMBINE_GEOM = Initiator Geometry Only
    FORMAT = POSTGRES
    COMBINE_ATTRS = Keep Initiator Attributes if Conflict
    EXPOSED_ATTRIBUTE_LIST = code,codes_id
    POSTGRES_HOST = $(config_host)
    RESULT -> Reprojector
Reprojector
    SOURCE = Read from feature
    RASTER_CELL_SIZE = Preserve Cells
    DEST = EPSG:32633
    INTERPOLATION_TYPE_NAME = Nearest Neighbor
    REPROJECTED -> SpatialRelator [Supplier]
SpatialRelator
    LIST_ATTRS_TO_INCLUDE = code codes_id
    CURVE_BOUNDARY_RULE_PARAM = Default Rule
    SUCCESS_ATTR = _related_candidates
    PREDICATES = INTERSECTS
    LIST_NAME = _relationships
    AGGREGATE_HANDLING = Yes
    CALC_CARD = No
    -> ListExploder
ListExploder
    ATTR_CONFLICT_RES = Use List Attribute Values
    INDEX_ATTR = _element_index
    LIST_ATTR = _relationships{}
    ATTR_ACCUM_MODE = Merge List Attributes
    ELEMENTS -> AttributeKeeper
    <REJECTED> -> ListExploder__Rejected_
AttributeKeeper
    KEEP_ATTRS = code,codes_id,geometry_id
    -> DuplicateFilter
DuplicateFilter
    KEYATTR = codes_id geometry_id
    INPUT_ORDERED_CHOICE = No
    UNIQUE -> codes_geometry (writer POSTGIS_1)
codes_geometry (writer POSTGIS_1)
    attributes: codes_id text, geometry_id text, code text
ListExploder__Rejected_: Inspector
