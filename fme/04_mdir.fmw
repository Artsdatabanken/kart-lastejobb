FME workspace 04_mdir.fmw

Parameters:
- SourceDataset_ESRISHAPE = D:\in\MDIR\Verneområder\NB3eksport\naturvernomrader_utm33.shp   # Source Esri Shapefile(s)
- config_pass:   # Python Script
      import fme
      import json
      
      data = json.load(open('../config/postgis.json'))
      
      return data['pass']
- config_user:   # Python Script
      import fme
      import json
      
      data = json.load(open('../config/postgis.json'))
      
      return data['user']
- config_db:   # Python Script
      import fme
      import json
      
      data = json.load(open('../config/postgis.json'))
      
      return data['db']
- config_port:   # Python Script
      import fme
      import json
      
      data = json.load(open('../config/postgis.json'))
      
      return data['port']
- config_host:   # Python Script
      import fme
      import json
      
      data = json.load(open('../config/postgis.json'))
      
      return data['host']
- Dataset = mdir

Readers:
- ESRISHAPE_1: ESRISHAPE from $(SourceDataset_ESRISHAPE)

Writers:
- POSTGIS_1: POSTGIS to $(config_db)

naturvernomrader_utm33 (reader ESRISHAPE_1)
    attributes: IID char(10), OMRADENAVN char(100), VERNEDATO date, VERNEF_ID char(5), VERNEFORM char(55), VERNEPLAN char(100), FORVALTNI char(30), REVISJON char(50), DATO_REVID date, TRUETVURD char(20), IUCN char(10), MOBLANDPRI char(50)
    -> Sampler
Sampler
    SAMPLE_TYPE_LONG = First N Features
    SAMPLE_MODE = No
    RATE = 1
    SAMPLED -> SQLExecutor_4 [INITIATOR]
    NOT_SAMPLED -> AttributeKeeper_2
Note: Insert prefix and dataset
SQLExecutor_4
    POSTGRES_PASSWORD = $(config_pass)
    SQL_STATEMENT:
      INSERT INTO data.prefix (value, description) values ('VV', 'Verneområder');
      INSERT INTO data.dataset (prefix_id, description) Select id, '$(Dataset)' from data.prefix where value = 'VV';
    POSTGRES_HOST = $(config_host)
    DATASET = $(config_db)
    POSTGRES_USER_NAME = $(config_user)
    FORMAT = POSTGRES
    COMBINE_GEOM = Initiator Geometry Only
    POSTGRES_SCHEMAS_FOR_TABLE_LISTING = data
    COMBINE_ATTRS = Keep Initiator Attributes if Conflict
    POSTGRES_PORT = $(config_port)
    POSTGRES_QUERY_FEATURE_TYPES_FOR_MERGE_FILTERS = Yes
    INITIATOR -> AttributeKeeper_2
AttributeKeeper_2
    KEEP_ATTRS = OMRADENAVN,IID
    -> AttributeRenamer
AttributeRenamer
    ATTR_TABLE:
      RENAME_SET_DEFAULT IID > code = VV_@Value(IID)
      RENAME_SET_DEFAULT OMRADENAVN > title
    -> Reprojector
Reprojector
    INTERPOLATION_TYPE_NAME = Nearest Neighbor
    SOURCE = Read from feature
    DEST = EPSG:4326
    RASTER_CELL_SIZE = Preserve Cells
    REPROJECTED -> SQLExecutor_2 [INITIATOR]
Note: Get id for pk
SQLExecutor_2
    POSTGRES_PASSWORD = $(config_pass)
    SQL_STATEMENT = SELECT nextval('data.geometry_id_seq') as id
    POSTGRES_HOST = $(config_host)
    DATASET = $(config_db)
    POSTGRES_USER_NAME = $(config_user)
    FORMAT = POSTGRES
    EXPOSED_ATTRIBUTE_LIST = id
    COMBINE_GEOM = Initiator Geometry Only
    POSTGRES_SCHEMAS_FOR_TABLE_LISTING = data
    COMBINE_ATTRS = Keep Initiator Attributes if Conflict
    POSTGRES_PORT = $(config_port)
    POSTGRES_QUERY_FEATURE_TYPES_FOR_MERGE_FILTERS = Yes
    RESULT -> SQLExecutor [INITIATOR]
    RESULT -> AttributeRenamer_4
Note: Get dataset id
SQLExecutor
    POSTGRES_PASSWORD =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
    SQL_STATEMENT = select id as dataset_id from data.dataset where description='$(Dataset)';
    POSTGRES_HOST = localhost
    DATASET = bigbadabom
    POSTGRES_USER_NAME = postgres
    FORMAT = POSTGRES
    EXPOSED_ATTRIBUTE_LIST = dataset_id
    COMBINE_GEOM = Initiator Geometry Only
    POSTGRES_SCHEMAS_FOR_TABLE_LISTING = data
    COMBINE_ATTRS = Keep Initiator Attributes if Conflict
    POSTGRES_PORT = 5432
    POSTGRES_QUERY_FEATURE_TYPES_FOR_MERGE_FILTERS = Yes
    RESULT -> geometry (writer POSTGIS_1)
geometry (writer POSTGIS_1)
    attributes: dataset_id int8, id int8
AttributeRenamer_4
    ATTR_TABLE = RENAME_SET_DEFAULT id > geometry_id
    -> FeatureHolder
FeatureHolder
    -> PythonCaller
Note: Fix single quotes before inserting
PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              title = feature.getAttribute('title')
              title = title.replace("'","''")
              feature.setAttribute('title', title)
              self.pyoutput(feature)
          def close(self):
              pass
    PYTHONSYMBOL = FeatureProcessor
    -> SQLExecutor_3 [INITIATOR]
Note: Insert VV-codes
SQLExecutor_3
    POSTGRES_PASSWORD = $(config_pass)
    SQL_STATEMENT = INSERT INTO data.codes (code, title) select '@Value(code)', '@Value(title)' WHERE NOT EXISTS (SELECT 1 FROM data.codes WHERE code = '@Value(code)');
    POSTGRES_HOST = $(config_host)
    DATASET = $(config_db)
    POSTGRES_USER_NAME = $(config_user)
    FORMAT = POSTGRES
    COMBINE_GEOM = Initiator Geometry Only
    POSTGRES_SCHEMAS_FOR_TABLE_LISTING = data
    COMBINE_ATTRS = Keep Result Attributes if Conflict
    POSTGRES_PORT = $(config_port)
    POSTGRES_QUERY_FEATURE_TYPES_FOR_MERGE_FILTERS = Yes
    INITIATOR -> SQLExecutor_5 [INITIATOR]
Note: Get code-id
SQLExecutor_5
    POSTGRES_PASSWORD = $(config_pass)
    SQL_STATEMENT = select id as codes_id from data.codes where code = '@Value(code)';
    POSTGRES_HOST = $(config_host)
    DATASET = $(config_db)
    POSTGRES_USER_NAME = $(config_user)
    FORMAT = POSTGRES
    EXPOSED_ATTRIBUTE_LIST = codes_id
    COMBINE_GEOM = Initiator Geometry Only
    POSTGRES_SCHEMAS_FOR_TABLE_LISTING = data
    COMBINE_ATTRS = Keep Result Attributes if Conflict
    POSTGRES_PORT = $(config_port)
    POSTGRES_QUERY_FEATURE_TYPES_FOR_MERGE_FILTERS = Yes
    RESULT -> codes_geometry (writer POSTGIS_1)
codes_geometry (writer POSTGIS_1)
    attributes: codes_id text, geometry_id text
